KENTIXDEVICES DEFINITIONS ::= BEGIN
IMPORTS
	Counter32, Unsigned32, Gauge32, Opaque, Integer32, OBJECT-TYPE, TimeTicks, enterprises, MODULE-IDENTITY, OBJECT-IDENTITY, NOTIFICATION-TYPE
		FROM SNMPv2-SMI
	TEXTUAL-CONVENTION, DisplayString, TruthValue
		FROM SNMPv2-TC;

kentix MODULE-IDENTITY
	LAST-UPDATED "202510290000Z"
	ORGANIZATION "Kentix GmbH"
	CONTACT-INFO "info@kentix.com"
	DESCRIPTION  "MIB of the Kentix devices"

	REVISION "202304120000Z"
	DESCRIPTION
			"Minor improvements/adjustments"

	REVISION "202510290000Z"
	DESCRIPTION
			"Change the mib to support the SMIv2 standards"
::= { enterprises 37954 }

-------------------------------------------------------------------------------------------

kentixdevices  OBJECT IDENTIFIER ::= { kentix 5 }

-------------------------------------------------------------------------------------------

-------------------------------------------------------------------------------------------
-- Top-Level
-------------------------------------------------------------------------------------------

system          OBJECT IDENTIFIER ::= { kentixdevices 1 }
valuemultiplier OBJECT IDENTIFIER ::= { system 1 }
alarmstate      OBJECT IDENTIFIER ::= { system 2 }
settings        OBJECT IDENTIFIER ::= { system 4 }
sensors         OBJECT IDENTIFIER ::= { kentixdevices 2 }
inputs          OBJECT IDENTIFIER ::= { sensors 100 }
outputs         OBJECT IDENTIFIER ::= { sensors 101 }
phases          OBJECT IDENTIFIER ::= { sensors 102 }
analoginputs    OBJECT IDENTIFIER ::= { sensors 103 }
leakages        OBJECT IDENTIFIER ::= { sensors 104 }
phase1          OBJECT IDENTIFIER ::= { phases 1 }
phase2          OBJECT IDENTIFIER ::= { phases 2 }
phase3          OBJECT IDENTIFIER ::= { phases 3 }
groups          OBJECT IDENTIFIER ::= { kentixdevices 3 }
logbook         OBJECT IDENTIFIER ::= { kentixdevices 4 }
rackunits       OBJECT IDENTIFIER ::= { kentixdevices 5 }
trapObjects     OBJECT IDENTIFIER ::= { kentixdevices 99 }


-------------------------------------------------------------------------------------------
-- Value Multiplier
-------------------------------------------------------------------------------------------

multiplierTemperature OBJECT-TYPE
SYNTAX          Unsigned32
MAX-ACCESS      read-write
STATUS          current
DESCRIPTION     "Multiplier for temperature measurements."
::= { valuemultiplier 1}

multiplierHumidity OBJECT-TYPE
SYNTAX          Unsigned32
MAX-ACCESS      read-write
STATUS          current
DESCRIPTION     "Multiplier for humidity measurements."
::= { valuemultiplier 2}

multiplierDewpoint OBJECT-TYPE
SYNTAX          Unsigned32
MAX-ACCESS      read-write
STATUS          current
DESCRIPTION     "Multiplier for dew point measurements."
::= { valuemultiplier 3}

multiplierVoltage OBJECT-TYPE
SYNTAX          Unsigned32
MAX-ACCESS      read-write
STATUS          current
DESCRIPTION     "Multiplier for voltage measurements."
::= { valuemultiplier 5}

multiplierCurrent OBJECT-TYPE
SYNTAX          Unsigned32
MAX-ACCESS      read-write
STATUS          current
DESCRIPTION     "Multiplier for current measurements."
::= { valuemultiplier 6}

multiplierActivepower OBJECT-TYPE
SYNTAX          Unsigned32
MAX-ACCESS      read-write
STATUS          current
DESCRIPTION     "Multiplier for activepower measurements."
::= { valuemultiplier 7}

multiplierReactivepower OBJECT-TYPE
SYNTAX          Unsigned32
MAX-ACCESS      read-write
STATUS          current
DESCRIPTION     "Multiplier for reactivepower measurements."
::= { valuemultiplier 8}

multiplierApparent OBJECT-TYPE
SYNTAX          Unsigned32
MAX-ACCESS      read-write
STATUS          current
DESCRIPTION     "Multiplier for apparent measurements."
::= { valuemultiplier 9}

multiplierFrequency OBJECT-TYPE
SYNTAX          Unsigned32
MAX-ACCESS      read-write
STATUS          current
DESCRIPTION     "Multiplier for frequency measurements."
::= { valuemultiplier 10}

multiplierConsumption OBJECT-TYPE
SYNTAX          Unsigned32
MAX-ACCESS      read-write
STATUS          current
DESCRIPTION     "Multiplier for consumption measurements."
::= { valuemultiplier 11}

multiplierPue OBJECT-TYPE
SYNTAX          Unsigned32
MAX-ACCESS      read-write
STATUS          current
DESCRIPTION     "Multiplier for pue measurements."
::= { valuemultiplier 12}

multiplierCo2 OBJECT-TYPE
SYNTAX          Unsigned32
MAX-ACCESS      read-write
STATUS          current
DESCRIPTION     "Multiplier for co2 measurements."
::= { valuemultiplier 13}

multiplierRcmAc OBJECT-TYPE
SYNTAX          Unsigned32
MAX-ACCESS      read-write
STATUS          current
DESCRIPTION     "Multiplier for rcm ac measurements."
::= { valuemultiplier 14}

multiplierRcmDc OBJECT-TYPE
SYNTAX          Unsigned32
MAX-ACCESS      read-write
STATUS          current
DESCRIPTION     "Multiplier for rcm dc measurements."
::= { valuemultiplier 15}


-------------------------------------------------------------------------------------------
-- Alarmstate
-------------------------------------------------------------------------------------------

alarmarmed OBJECT-TYPE
SYNTAX          TruthValue
MAX-ACCESS      read-write
STATUS          current
DESCRIPTION     "Alarm state for armed alarms."
::= { alarmstate 1}

alarmalways OBJECT-TYPE
SYNTAX          TruthValue
MAX-ACCESS      read-write
STATUS          current
DESCRIPTION     "Alarm state for always alarms."
::= { alarmstate 2}

serverstate OBJECT-TYPE
SYNTAX          TruthValue
MAX-ACCESS      read-write
STATUS          current
DESCRIPTION     "State for serverpolling."
::= { alarmstate 3}

sensorcommunication OBJECT-TYPE
SYNTAX          TruthValue
MAX-ACCESS      read-write
STATUS          current
DESCRIPTION     "State for sensor communication."
::= { alarmstate 4}

alarmsabotage OBJECT-TYPE
SYNTAX          TruthValue
MAX-ACCESS      read-write
STATUS          current
DESCRIPTION     "Alarm state for sabotage alarms."
::= { alarmstate 5}

gsmsignal OBJECT-TYPE
SYNTAX          TruthValue
MAX-ACCESS      read-write
STATUS          current
DESCRIPTION     "Strength of the GSM signal."
::= { alarmstate 6}

gsmok OBJECT-TYPE
SYNTAX          TruthValue
MAX-ACCESS      read-write
STATUS          current
DESCRIPTION     "State for the GSM provider."
::= { alarmstate 7}

systemarmed OBJECT-TYPE
SYNTAX          TruthValue
MAX-ACCESS      read-write
STATUS          current
DESCRIPTION     "Value true if all groups are armed."
::= { alarmstate 8}

alarmtemp OBJECT-TYPE
SYNTAX          TruthValue
MAX-ACCESS      read-write
STATUS          current
DESCRIPTION     "Collective alarm for temperature."
::= { alarmstate 9}

alarmhum OBJECT-TYPE
SYNTAX          TruthValue
MAX-ACCESS      read-write
STATUS          current
DESCRIPTION     "Collective alarm for humidity."
::= { alarmstate 10}

alarmdewpoint OBJECT-TYPE
SYNTAX          TruthValue
MAX-ACCESS      read-write
STATUS          current
DESCRIPTION     "Collective alarm for dewpoint."
::= { alarmstate 11}

alarmco OBJECT-TYPE
SYNTAX          TruthValue
MAX-ACCESS      read-write
STATUS          current
DESCRIPTION     "Collective alarm for co."
::= { alarmstate 12}

alarmvoltage OBJECT-TYPE
SYNTAX          TruthValue
MAX-ACCESS      read-write
STATUS          current
DESCRIPTION     "Collective alarm for voltage."
::= { alarmstate 13}

alarmcurrent OBJECT-TYPE
SYNTAX          TruthValue
MAX-ACCESS      read-write
STATUS          current
DESCRIPTION     "Collective alarm for current."
::= { alarmstate 14}

alarmfrequency OBJECT-TYPE
SYNTAX          TruthValue
MAX-ACCESS      read-write
STATUS          current
DESCRIPTION     "Collective alarm for frequency."
::= { alarmstate 15}

alarmactivpower OBJECT-TYPE
SYNTAX          TruthValue
MAX-ACCESS      read-write
STATUS          current
DESCRIPTION     "Collective alarm for active power."
::= { alarmstate 16}

alarmreactivepower OBJECT-TYPE
SYNTAX          TruthValue
MAX-ACCESS      read-write
STATUS          current
DESCRIPTION     "Collective alarm for reactive power."
::= { alarmstate 17}

alarmapparentpower OBJECT-TYPE
SYNTAX          TruthValue
MAX-ACCESS      read-write
STATUS          current
DESCRIPTION     "Collective alarm for apparent power."
::= { alarmstate 18}

alarmfire OBJECT-TYPE
SYNTAX          TruthValue
MAX-ACCESS      read-write
STATUS          current
DESCRIPTION     "Alarm state for fire alarms."
::= { alarmstate 19}

alarmsystem OBJECT-TYPE
SYNTAX          TruthValue
MAX-ACCESS      read-write
STATUS          current
DESCRIPTION     "Alarm state for system alarms."
::= { alarmstate 20}

-------------------------------------------------------------------------------------------
-- Settings
-------------------------------------------------------------------------------------------

temperatureUnit OBJECT-TYPE
SYNTAX          DisplayString
MAX-ACCESS      read-write
STATUS          current
DESCRIPTION     "Temperature unit of the system."
::= { settings 1}


-------------------------------------------------------------------------------------------
-- Sensors
-------------------------------------------------------------------------------------------

-------------------------------------------------------------------------------------------
-- Sensor general
-------------------------------------------------------------------------------------------

generalTable OBJECT-TYPE
SYNTAX          SEQUENCE OF GeneralEntry
MAX-ACCESS      not-accessible
STATUS          current
DESCRIPTION     "General values."
::= { sensors 1 }

generalEntry OBJECT-TYPE
SYNTAX          GeneralEntry
MAX-ACCESS      not-accessible
STATUS          current
DESCRIPTION     "Entry in general table."
INDEX        { generalIndex }
::= { generalTable 1 }

GeneralEntry ::= SEQUENCE {
generalIndex			Unsigned32,
sensorName				DisplayString,
sensorType				DisplayString,
sensorVersion			DisplayString,
sensorAddress			DisplayString,
sensorPort				Unsigned32,
sensorGroup				DisplayString,
sensorMacAddress		DisplayString,
sensorDescription		DisplayString}

generalIndex OBJECT-TYPE
SYNTAX          Unsigned32
MAX-ACCESS      not-accessible
STATUS          current
DESCRIPTION     "Table Index."
::= { generalEntry 1}

sensorName OBJECT-TYPE
SYNTAX          DisplayString
MAX-ACCESS      read-write
STATUS          current
DESCRIPTION     "Name of the sensor."
::= { generalEntry 2}

sensorType OBJECT-TYPE
SYNTAX          DisplayString
MAX-ACCESS      read-write
STATUS          current
DESCRIPTION     "Devicetype of the sensor."
::= { generalEntry 3}

sensorVersion OBJECT-TYPE
SYNTAX          DisplayString
MAX-ACCESS      read-write
STATUS          current
DESCRIPTION     "Version of the sensor."
::= { generalEntry 4}

sensorAddress OBJECT-TYPE
SYNTAX          DisplayString
MAX-ACCESS      read-write
STATUS          current
DESCRIPTION     "Address of the sensor."
::= { generalEntry 5}

sensorPort OBJECT-TYPE
SYNTAX          Unsigned32
MAX-ACCESS      read-write
STATUS          current
DESCRIPTION     "Sensor port."
::= { generalEntry 6}

sensorGroup OBJECT-TYPE
SYNTAX          DisplayString
MAX-ACCESS      read-write
STATUS          current
DESCRIPTION     "Sensor group."
::= { generalEntry 7}

sensorMacAddress OBJECT-TYPE
SYNTAX          DisplayString
MAX-ACCESS      read-write
STATUS          current
DESCRIPTION     "MacAddress of the sensor."
::= { generalEntry 10}

sensorDescription OBJECT-TYPE
SYNTAX          DisplayString
MAX-ACCESS      read-write
STATUS          current
DESCRIPTION     "Description of the sensor."
::= { generalEntry 11}

-------------------------------------------------------------------------------------------
-- Sensor temperature
-------------------------------------------------------------------------------------------

temperatureTable OBJECT-TYPE
SYNTAX          SEQUENCE OF TemperatureEntry
MAX-ACCESS      not-accessible
STATUS          current
DESCRIPTION     "Temperature values."
::= { sensors 2 }

temperatureEntry OBJECT-TYPE
SYNTAX          TemperatureEntry
MAX-ACCESS      not-accessible
STATUS          current
DESCRIPTION     "Entry in temperature table."
INDEX        { temperatureIndex }
::= { temperatureTable 1 }

TemperatureEntry ::= SEQUENCE {
temperatureIndex	Unsigned32,
tempValue			Integer32,
tempAlarm			Unsigned32,
tempMin				Integer32,
tempMax				Integer32,
tempTimestamp		Integer32}

temperatureIndex OBJECT-TYPE
SYNTAX          Unsigned32
MAX-ACCESS      not-accessible
STATUS          current
DESCRIPTION     "Table Index."
::= { temperatureEntry 1}

tempValue OBJECT-TYPE
SYNTAX          Integer32
MAX-ACCESS      read-write
STATUS          current
DESCRIPTION     "Current value."
::= { temperatureEntry 2}

tempAlarm OBJECT-TYPE
SYNTAX          Unsigned32
MAX-ACCESS      read-write
STATUS          current
DESCRIPTION     "Current alarmstate."
::= { temperatureEntry 3}

tempMin OBJECT-TYPE
SYNTAX          Integer32
MAX-ACCESS      read-write
STATUS          current
DESCRIPTION     "Min. threshold of this value."
::= { temperatureEntry 4}

tempMax OBJECT-TYPE
SYNTAX          Integer32
MAX-ACCESS      read-write
STATUS          current
DESCRIPTION     "Max. threshold of this value."
::= { temperatureEntry 5}

tempTimestamp OBJECT-TYPE
SYNTAX          Integer32
MAX-ACCESS      read-write
STATUS          current
DESCRIPTION     "Timestamp of alarmstate change."
::= { temperatureEntry 10}

-------------------------------------------------------------------------------------------
-- Sensor humidity
-------------------------------------------------------------------------------------------

humidityTable OBJECT-TYPE
SYNTAX          SEQUENCE OF HumidityEntry
MAX-ACCESS      not-accessible
STATUS          current
DESCRIPTION     "Humidity values."
::= { sensors 3 }

humidityEntry OBJECT-TYPE
SYNTAX          HumidityEntry
MAX-ACCESS      not-accessible
STATUS          current
DESCRIPTION     "Entry in humidity table."
INDEX        { humidityIndex }
::= { humidityTable 1 }

HumidityEntry ::= SEQUENCE {
humidityIndex	Unsigned32,
humValue		Unsigned32,
humAlarm		Unsigned32,
humMin			Unsigned32,
humMax			Unsigned32,
humTimestamp	Integer32}

humidityIndex OBJECT-TYPE
SYNTAX          Unsigned32
MAX-ACCESS      not-accessible
STATUS          current
DESCRIPTION     "Table Index."
::= { humidityEntry 1}

humValue OBJECT-TYPE
SYNTAX          Unsigned32
MAX-ACCESS      read-write
STATUS          current
DESCRIPTION     "Current value."
::= { humidityEntry 2}

humAlarm OBJECT-TYPE
SYNTAX          Unsigned32
MAX-ACCESS      read-write
STATUS          current
DESCRIPTION     "Current alarmstate."
::= { humidityEntry 3}

humMin OBJECT-TYPE
SYNTAX          Unsigned32
MAX-ACCESS      read-write
STATUS          current
DESCRIPTION     "Min. threshold of this value."
::= { humidityEntry 4}

humMax OBJECT-TYPE
SYNTAX          Unsigned32
MAX-ACCESS      read-write
STATUS          current
DESCRIPTION     "Max. threshold of this value."
::= { humidityEntry 5}

humTimestamp OBJECT-TYPE
SYNTAX          Integer32
MAX-ACCESS      read-write
STATUS          current
DESCRIPTION     "Timestamp of alarmstate change."
::= { humidityEntry 10}

-------------------------------------------------------------------------------------------
-- Sensor dewpoint
-------------------------------------------------------------------------------------------

dewpointTable OBJECT-TYPE
SYNTAX          SEQUENCE OF DewpointEntry
MAX-ACCESS      not-accessible
STATUS          current
DESCRIPTION     "Dewpoint values."
::= { sensors 4 }

dewpointEntry OBJECT-TYPE
SYNTAX          DewpointEntry
MAX-ACCESS      not-accessible
STATUS          current
DESCRIPTION     "Entry in dewpoint table."
INDEX        { dewpointIndex }
::= { dewpointTable 1 }

DewpointEntry ::= SEQUENCE {
dewpointIndex	Unsigned32,
dewValue		Integer32,
dewAlarm		Unsigned32,
dewMax			Integer32,
dewTimestamp	Integer32}

dewpointIndex OBJECT-TYPE
SYNTAX          Unsigned32
MAX-ACCESS      not-accessible
STATUS          current
DESCRIPTION     "Table Index."
::= { dewpointEntry 1}

dewValue OBJECT-TYPE
SYNTAX          Integer32
MAX-ACCESS      read-write
STATUS          current
DESCRIPTION     "Current value."
::= { dewpointEntry 2}

dewAlarm OBJECT-TYPE
SYNTAX          Unsigned32
MAX-ACCESS      read-write
STATUS          current
DESCRIPTION     "Current alarmstate."
::= { dewpointEntry 3}

dewMax OBJECT-TYPE
SYNTAX          Integer32
MAX-ACCESS      read-write
STATUS          current
DESCRIPTION     "Max. hysterese to the temperature value."
::= { dewpointEntry 5}

dewTimestamp OBJECT-TYPE
SYNTAX          Integer32
MAX-ACCESS      read-write
STATUS          current
DESCRIPTION     "Timestamp of alarmstate change."
::= { dewpointEntry 10}

-------------------------------------------------------------------------------------------
-- Sensor Co
-------------------------------------------------------------------------------------------

coTable OBJECT-TYPE
SYNTAX          SEQUENCE OF CoEntry
MAX-ACCESS      not-accessible
STATUS          current
DESCRIPTION     "CO values."
::= { sensors 5 }

coEntry OBJECT-TYPE
SYNTAX          CoEntry
MAX-ACCESS      not-accessible
STATUS          current
DESCRIPTION     "Entry in co table."
INDEX        { coIndex }
::= { coTable 1 }

CoEntry ::= SEQUENCE {
coIndex			Unsigned32,
coValue			Unsigned32,
coAlarm			Unsigned32,
coMax			Unsigned32,
coTimestamp		Integer32}

coIndex OBJECT-TYPE
SYNTAX          Unsigned32
MAX-ACCESS      not-accessible
STATUS          current
DESCRIPTION     "Table Index."
::= { coEntry 1}

coValue OBJECT-TYPE
SYNTAX          Unsigned32
MAX-ACCESS      read-write
STATUS          current
DESCRIPTION     "Current value."
::= { coEntry 2}

coAlarm OBJECT-TYPE
SYNTAX          Unsigned32
MAX-ACCESS      read-write
STATUS          current
DESCRIPTION     "Current alarmstate."
::= { coEntry 3}

coMax OBJECT-TYPE
SYNTAX          Unsigned32
MAX-ACCESS      read-write
STATUS          current
DESCRIPTION     "Max. threshold of this value."
::= { coEntry 5}

coTimestamp OBJECT-TYPE
SYNTAX          Integer32
MAX-ACCESS      read-write
STATUS          current
DESCRIPTION     "Timestamp of alarmstate change."
::= { coEntry 10}

-------------------------------------------------------------------------------------------
-- Sensor motion.
-------------------------------------------------------------------------------------------

motionTable OBJECT-TYPE
SYNTAX          SEQUENCE OF MotionEntry
MAX-ACCESS      not-accessible
STATUS          current
DESCRIPTION     "Motion values."
::= { sensors 6 }

motionEntry OBJECT-TYPE
SYNTAX          MotionEntry
MAX-ACCESS      not-accessible
STATUS          current
DESCRIPTION     "Entry in motion table."
INDEX        { motionIndex }
::= { motionTable 1 }

MotionEntry ::= SEQUENCE {
motionIndex		Unsigned32,
motValue		Unsigned32,
motAlarm		Unsigned32,
motMax			Unsigned32,
motTimestamp	Integer32}

motionIndex OBJECT-TYPE
SYNTAX          Unsigned32
MAX-ACCESS      not-accessible
STATUS          current
DESCRIPTION     "Table Index."
::= { motionEntry 1}

motValue OBJECT-TYPE
SYNTAX          Unsigned32
MAX-ACCESS      read-write
STATUS          current
DESCRIPTION     "Current value."
::= { motionEntry 2}

motAlarm OBJECT-TYPE
SYNTAX          Unsigned32
MAX-ACCESS      read-write
STATUS          current
DESCRIPTION     "Current alarmstate."
::= { motionEntry 3}

motMax OBJECT-TYPE
SYNTAX          Unsigned32
MAX-ACCESS      read-write
STATUS          current
DESCRIPTION     "Max. threshold of this value."
::= { motionEntry 5}

motTimestamp OBJECT-TYPE
SYNTAX          Integer32
MAX-ACCESS      read-write
STATUS          current
DESCRIPTION     "Timestamp of alarmstate change."
::= { motionEntry 10}

-------------------------------------------------------------------------------------------
-- Sensor vibration.
-------------------------------------------------------------------------------------------

vibrationTable OBJECT-TYPE
SYNTAX          SEQUENCE OF VibrationEntry
MAX-ACCESS      not-accessible
STATUS          current
DESCRIPTION     "Vibration values."
::= { sensors 7 }

vibrationEntry OBJECT-TYPE
SYNTAX          VibrationEntry
MAX-ACCESS      not-accessible
STATUS          current
DESCRIPTION     "Entry in vibration table."
INDEX        { vibrationIndex }
::= { vibrationTable 1 }

VibrationEntry ::= SEQUENCE {
vibrationIndex	Unsigned32,
vibValue		Unsigned32,
vibAlarm		Unsigned32,
vibLogic		Unsigned32,
vibTimestamp	Integer32}

vibrationIndex OBJECT-TYPE
SYNTAX          Unsigned32
MAX-ACCESS      not-accessible
STATUS          current
DESCRIPTION     "Table Index."
::= { vibrationEntry 1}

vibValue OBJECT-TYPE
SYNTAX          Unsigned32
MAX-ACCESS      read-write
STATUS          current
DESCRIPTION     "Current value."
::= { vibrationEntry 2}

vibAlarm OBJECT-TYPE
SYNTAX          Unsigned32
MAX-ACCESS      read-write
STATUS          current
DESCRIPTION     "Current alarmstate."
::= { vibrationEntry 3}

vibLogic OBJECT-TYPE
SYNTAX          Unsigned32
MAX-ACCESS      read-write
STATUS          current
DESCRIPTION     "Logic of this value."
::= { vibrationEntry 5}

vibTimestamp OBJECT-TYPE
SYNTAX          Integer32
MAX-ACCESS      read-write
STATUS          current
DESCRIPTION     "Timestamp of alarmstate change."
::= { vibrationEntry 10}

-------------------------------------------------------------------------------------------
-- Sensor latency
-------------------------------------------------------------------------------------------

latencyTable OBJECT-TYPE
SYNTAX          SEQUENCE OF LatencyEntry
MAX-ACCESS      not-accessible
STATUS          current
DESCRIPTION     "Latency values for the network monitoring."
::= { sensors 8 }

latencyEntry OBJECT-TYPE
SYNTAX          LatencyEntry
MAX-ACCESS      not-accessible
STATUS          current
DESCRIPTION     "Entry in latency table."
INDEX        { latencyIndex }
::= { latencyTable 1 }

LatencyEntry ::= SEQUENCE {
latencyIndex	Unsigned32,
latValue		Unsigned32,
latAlarm		Unsigned32,
latMax			Unsigned32,
latTimestamp	Integer32}

latencyIndex OBJECT-TYPE
SYNTAX          Unsigned32
MAX-ACCESS      not-accessible
STATUS          current
DESCRIPTION     "Table Index."
::= { latencyEntry 1}

latValue OBJECT-TYPE
SYNTAX          Unsigned32
MAX-ACCESS      read-write
STATUS          current
DESCRIPTION     "Current value."
::= { latencyEntry 2}

latAlarm OBJECT-TYPE
SYNTAX          Unsigned32
MAX-ACCESS      read-write
STATUS          current
DESCRIPTION     "Current alarmstate."
::= { latencyEntry 3}

latMax OBJECT-TYPE
SYNTAX          Unsigned32
MAX-ACCESS      read-write
STATUS          current
DESCRIPTION     "Max. threshold of this value."
::= { latencyEntry 5}

latTimestamp OBJECT-TYPE
SYNTAX          Integer32
MAX-ACCESS      read-write
STATUS          current
DESCRIPTION     "Timestamp of alarmstate change."
::= { latencyEntry 10}

-------------------------------------------------------------------------------------------
-- Sensor SNMP Logic
-------------------------------------------------------------------------------------------

snmpLogicTable OBJECT-TYPE
SYNTAX          SEQUENCE OF SnmpLogicEntry
MAX-ACCESS      not-accessible
STATUS          current
DESCRIPTION     "SNMP retrieving values for the snmp monitoring."
::= { sensors 9 }

snmpLogicEntry OBJECT-TYPE
SYNTAX          SnmpLogicEntry
MAX-ACCESS      not-accessible
STATUS          current
DESCRIPTION     "Entry in snmpLogic table."
INDEX        { snmpLogicIndex }
::= { snmpLogicTable 1 }

SnmpLogicEntry ::= SEQUENCE {
snmpLogicIndex		Unsigned32,
snmpLogicName		DisplayString,
snmpLogicGroup		DisplayString,
snmpLogicValue		Unsigned32,
snmpLogicAlarm		Unsigned32,
snmpLogicLogic		Unsigned32,
snmpLogicTimestamp	Integer32}

snmpLogicIndex OBJECT-TYPE
SYNTAX          Unsigned32
MAX-ACCESS      not-accessible
STATUS          current
DESCRIPTION     "Table Index."
::= { snmpLogicEntry 1}

snmpLogicName OBJECT-TYPE
SYNTAX          DisplayString
MAX-ACCESS      read-write
STATUS          current
DESCRIPTION     "Name of this value."
::= { snmpLogicEntry 2}

snmpLogicGroup OBJECT-TYPE
SYNTAX          DisplayString
MAX-ACCESS      read-write
STATUS          current
DESCRIPTION     "Alarmgroup of this value."
::= { snmpLogicEntry 3}

snmpLogicValue OBJECT-TYPE
SYNTAX          Unsigned32
MAX-ACCESS      read-write
STATUS          current
DESCRIPTION     "Current value."
::= { snmpLogicEntry 4}

snmpLogicAlarm OBJECT-TYPE
SYNTAX          Unsigned32
MAX-ACCESS      read-write
STATUS          current
DESCRIPTION     "Current alarmstate."
::= { snmpLogicEntry 5}

snmpLogicLogic OBJECT-TYPE
SYNTAX          Unsigned32
MAX-ACCESS      read-write
STATUS          current
DESCRIPTION     "Logic of this value."
::= { snmpLogicEntry 6}

snmpLogicTimestamp OBJECT-TYPE
SYNTAX          Integer32
MAX-ACCESS      read-write
STATUS          current
DESCRIPTION     "Timestamp of alarmstate change."
::= { snmpLogicEntry 10}

-------------------------------------------------------------------------------------------
-- Sensor SNMP Value
-------------------------------------------------------------------------------------------

snmpValueTable OBJECT-TYPE
SYNTAX          SEQUENCE OF SnmpValueEntry
MAX-ACCESS      not-accessible
STATUS          current
DESCRIPTION     "SNMP retrieving values for the snmp monitoring."
::= { sensors 10 }

snmpValueEntry OBJECT-TYPE
SYNTAX          SnmpValueEntry
MAX-ACCESS      not-accessible
STATUS          current
DESCRIPTION     "Entry in snmpValue table."
INDEX        { snmpValueIndex }
::= { snmpValueTable 1 }

SnmpValueEntry ::= SEQUENCE {
snmpValueIndex		Unsigned32,
snmpValueName		DisplayString,
snmpValueGroup		DisplayString,
snmpValueValue		Integer32,
snmpValueAlarm		Unsigned32,
snmpValueMin		Integer32,
snmpValueMax		Integer32,
snmpValueUnit		DisplayString,
snmpValueMultiplier	Unsigned32,
snmpValueTimestamp	Integer32}

snmpValueIndex OBJECT-TYPE
SYNTAX          Unsigned32
MAX-ACCESS      not-accessible
STATUS          current
DESCRIPTION     "Table Index."
::= { snmpValueEntry 1}

snmpValueName OBJECT-TYPE
SYNTAX          DisplayString
MAX-ACCESS      read-write
STATUS          current
DESCRIPTION     "Name of this value."
::= { snmpValueEntry 2}

snmpValueGroup OBJECT-TYPE
SYNTAX          DisplayString
MAX-ACCESS      read-write
STATUS          current
DESCRIPTION     "Alarmgroup of this value."
::= { snmpValueEntry 3}

snmpValueValue OBJECT-TYPE
SYNTAX          Integer32
MAX-ACCESS      read-write
STATUS          current
DESCRIPTION     "Current value."
::= { snmpValueEntry 4}

snmpValueAlarm OBJECT-TYPE
SYNTAX          Unsigned32
MAX-ACCESS      read-write
STATUS          current
DESCRIPTION     "Current alarmstate."
::= { snmpValueEntry 5}

snmpValueMin OBJECT-TYPE
SYNTAX          Integer32
MAX-ACCESS      read-write
STATUS          current
DESCRIPTION     "Min. threshold of this value."
::= { snmpValueEntry 6}

snmpValueMax OBJECT-TYPE
SYNTAX          Integer32
MAX-ACCESS      read-write
STATUS          current
DESCRIPTION     "Max. threshold of this value."
::= { snmpValueEntry 7}

snmpValueUnit OBJECT-TYPE
SYNTAX          DisplayString
MAX-ACCESS      read-write
STATUS          current
DESCRIPTION     "Unit of this value."
::= { snmpValueEntry 8}

snmpValueMultiplier OBJECT-TYPE
SYNTAX          Unsigned32
MAX-ACCESS      read-write
STATUS          current
DESCRIPTION     "Multiplier of this value."
::= { snmpValueEntry 9}

snmpValueTimestamp OBJECT-TYPE
SYNTAX          Integer32
MAX-ACCESS      read-write
STATUS          current
DESCRIPTION     "Timestamp of alarmstate change."
::= { snmpValueEntry 10}

-------------------------------------------------------------------------------------------
-- Sensor SNMP Display
-------------------------------------------------------------------------------------------

snmpDisplayTable OBJECT-TYPE
SYNTAX          SEQUENCE OF SnmpDisplayEntry
MAX-ACCESS      not-accessible
STATUS          current
DESCRIPTION     "SNMP retrieving values for the snmp monitoring."
::= { sensors 11 }

snmpDisplayEntry OBJECT-TYPE
SYNTAX          SnmpDisplayEntry
MAX-ACCESS      not-accessible
STATUS          current
DESCRIPTION     "Entry in snmpDisplay table."
INDEX        { snmpDisplayIndex }
::= { snmpDisplayTable 1 }

SnmpDisplayEntry ::= SEQUENCE {
snmpDisplayIndex	Unsigned32,
snmpDisplayName		DisplayString,
snmpDisplayGroup	DisplayString,
snmpDisplayValue	DisplayString,
snmpDisplayUnit		DisplayString}

snmpDisplayIndex OBJECT-TYPE
SYNTAX          Unsigned32
MAX-ACCESS      not-accessible
STATUS          current
DESCRIPTION     "Table Index."
::= { snmpDisplayEntry 1}

snmpDisplayName OBJECT-TYPE
SYNTAX          DisplayString
MAX-ACCESS      read-write
STATUS          current
DESCRIPTION     "Name of this value."
::= { snmpDisplayEntry 2}

snmpDisplayGroup OBJECT-TYPE
SYNTAX          DisplayString
MAX-ACCESS      read-write
STATUS          current
DESCRIPTION     "Alarmgroup of this value."
::= { snmpDisplayEntry 3}

snmpDisplayValue OBJECT-TYPE
SYNTAX          DisplayString
MAX-ACCESS      read-write
STATUS          current
DESCRIPTION     "Current value."
::= { snmpDisplayEntry 4}

snmpDisplayUnit OBJECT-TYPE
SYNTAX          DisplayString
MAX-ACCESS      read-write
STATUS          current
DESCRIPTION     "Unit of this value."
::= { snmpDisplayEntry 8}

-------------------------------------------------------------------------------------------
-- Sensor SNMP AlarmIf
-------------------------------------------------------------------------------------------

snmpAlarmIfTable OBJECT-TYPE
SYNTAX          SEQUENCE OF SnmpAlarmIfEntry
MAX-ACCESS      not-accessible
STATUS          current
DESCRIPTION     "SNMP retrieving values for the snmp monitoring."
::= { sensors 12 }

snmpAlarmIfEntry OBJECT-TYPE
SYNTAX          SnmpAlarmIfEntry
MAX-ACCESS      not-accessible
STATUS          current
DESCRIPTION     "Entry in snmpAlarmIf table."
INDEX        { snmpAlarmIfIndex }
::= { snmpAlarmIfTable 1 }

SnmpAlarmIfEntry ::= SEQUENCE {
snmpAlarmIfIndex		Unsigned32,
snmpAlarmIfName			DisplayString,
snmpAlarmIfGroup		DisplayString,
snmpAlarmIfValue		DisplayString,
snmpAlarmIfAlarm		Unsigned32,
snmpAlarmIfUnit			DisplayString,
snmpAlarmIfTimestamp	Integer32
}

snmpAlarmIfIndex OBJECT-TYPE
SYNTAX          Unsigned32
MAX-ACCESS      not-accessible
STATUS          current
DESCRIPTION     "Table Index."
::= { snmpAlarmIfEntry 1}

snmpAlarmIfName OBJECT-TYPE
SYNTAX          DisplayString
MAX-ACCESS      read-write
STATUS          current
DESCRIPTION     "Name of this value."
::= { snmpAlarmIfEntry 2}

snmpAlarmIfGroup OBJECT-TYPE
SYNTAX          DisplayString
MAX-ACCESS      read-write
STATUS          current
DESCRIPTION     "Alarmgroup of this value."
::= { snmpAlarmIfEntry 3}

snmpAlarmIfValue OBJECT-TYPE
SYNTAX          DisplayString
MAX-ACCESS      read-write
STATUS          current
DESCRIPTION     "Current value."
::= { snmpAlarmIfEntry 4}

snmpAlarmIfAlarm OBJECT-TYPE
SYNTAX          Unsigned32
MAX-ACCESS      read-write
STATUS          current
DESCRIPTION     "Current alarmstate."
::= { snmpAlarmIfEntry 5}

snmpAlarmIfUnit OBJECT-TYPE
SYNTAX          DisplayString
MAX-ACCESS      read-write
STATUS          current
DESCRIPTION     "Unit of this value."
::= { snmpAlarmIfEntry 8}

snmpAlarmIfTimestamp OBJECT-TYPE
SYNTAX          Integer32
MAX-ACCESS      read-write
STATUS          current
DESCRIPTION     "Timestamp of alarmstate change."
::= { snmpAlarmIfEntry 10}

-------------------------------------------------------------------------------------------
-- Sensor Latch State
-------------------------------------------------------------------------------------------

latchTable OBJECT-TYPE
SYNTAX          SEQUENCE OF LatchEntry
MAX-ACCESS      not-accessible
STATUS          current
DESCRIPTION     "Latch states."
::= { sensors 13 }

latchEntry OBJECT-TYPE
SYNTAX          LatchEntry
MAX-ACCESS      not-accessible
STATUS          current
DESCRIPTION     "Entry in latch table."
INDEX        { latchIndex }
::= { latchTable 1 }

LatchEntry ::= SEQUENCE {
latchIndex	    Unsigned32,
latchValue	    Integer32,
latchAlarm	    Unsigned32,
latchLogic	    Unsigned32,
latchTimestamp	Integer32}

latchIndex OBJECT-TYPE
SYNTAX          Unsigned32
MAX-ACCESS      not-accessible
STATUS          current
DESCRIPTION     "Table Index."
::= { latchEntry 1}

latchValue OBJECT-TYPE
SYNTAX          Integer32
MAX-ACCESS      read-write
STATUS          current
DESCRIPTION     "Current value."
::= { latchEntry 2}

latchAlarm OBJECT-TYPE
SYNTAX          Unsigned32
MAX-ACCESS      read-write
STATUS          current
DESCRIPTION     "Current alarmstate."
::= { latchEntry 3}

latchLogic OBJECT-TYPE
SYNTAX          Unsigned32
MAX-ACCESS      read-write
STATUS          current
DESCRIPTION     "Logic of this value."
::= { latchEntry 5}

latchTimestamp OBJECT-TYPE
SYNTAX          Integer32
MAX-ACCESS      read-write
STATUS          current
DESCRIPTION     "Timestamp of alarmstate change."
::= { latchEntry 10}

-------------------------------------------------------------------------------------------
-- Device Connection State
-------------------------------------------------------------------------------------------

connectionTable OBJECT-TYPE
SYNTAX          SEQUENCE OF ConnectionEntry
MAX-ACCESS      not-accessible
STATUS          current
DESCRIPTION     "Connection states."
::= { sensors 14 }

connectionEntry OBJECT-TYPE
SYNTAX          ConnectionEntry
MAX-ACCESS      not-accessible
STATUS          current
DESCRIPTION     "Entry in connection table."
INDEX        { connectionIndex }
::= { connectionTable 1 }

ConnectionEntry ::= SEQUENCE {
connectionIndex		Unsigned32,
connectionAlarm		Unsigned32,
connectionTimestamp	Integer32}

connectionIndex OBJECT-TYPE
SYNTAX          Unsigned32
MAX-ACCESS      not-accessible
STATUS          current
DESCRIPTION     "Table Index."
::= { connectionEntry 1}

connectionAlarm OBJECT-TYPE
SYNTAX          Unsigned32
MAX-ACCESS      read-write
STATUS          current
DESCRIPTION     "Current alarmstate."
::= { connectionEntry 3}

connectionTimestamp OBJECT-TYPE
SYNTAX          Integer32
MAX-ACCESS      read-write
STATUS          current
DESCRIPTION     "Timestamp of alarmstate change."
::= { connectionEntry 10}

-------------------------------------------------------------------------------------------
-- Sensor Fire (TI) State
-------------------------------------------------------------------------------------------

tiFireTable OBJECT-TYPE
SYNTAX          SEQUENCE OF TiFireEntry
MAX-ACCESS      not-accessible
STATUS          current
DESCRIPTION     "TI fire states."
::= { sensors 16 }

tiFireEntry OBJECT-TYPE
SYNTAX          TiFireEntry
MAX-ACCESS      not-accessible
STATUS          current
DESCRIPTION     "Entry in ti fire table."
INDEX        { tiFireIndex }
::= { tiFireTable 1 }

TiFireEntry ::= SEQUENCE {
tiFireIndex     Unsigned32,
tiFireValue     Integer32,
tiFireAlarm     Unsigned32,
tiFireMax       Integer32,
tiFireTimestamp	Integer32}

tiFireIndex OBJECT-TYPE
SYNTAX          Unsigned32
MAX-ACCESS      not-accessible
STATUS          current
DESCRIPTION     "Table Index."
::= { tiFireEntry 1}

tiFireValue OBJECT-TYPE
SYNTAX          Integer32
MAX-ACCESS      read-write
STATUS          current
DESCRIPTION     "Current value."
::= { tiFireEntry 2}

tiFireAlarm OBJECT-TYPE
SYNTAX          Unsigned32
MAX-ACCESS      read-write
STATUS          current
DESCRIPTION     "Current alarmstate."
::= { tiFireEntry 3}

tiFireMax OBJECT-TYPE
SYNTAX          Integer32
MAX-ACCESS      read-write
STATUS          current
DESCRIPTION     "Max. threshold of this value."
::= { tiFireEntry 5}

tiFireTimestamp OBJECT-TYPE
SYNTAX          Integer32
MAX-ACCESS      read-write
STATUS          current
DESCRIPTION     "Timestamp of alarmstate change."
::= { tiFireEntry 10}

-------------------------------------------------------------------------------------------
-- Sensor AirQuality State
-------------------------------------------------------------------------------------------

airQualityTable OBJECT-TYPE
SYNTAX          SEQUENCE OF AirQualityEntry
MAX-ACCESS      not-accessible
STATUS          current
DESCRIPTION     "Air quality states."
::= { sensors 17 }

airQualityEntry OBJECT-TYPE
SYNTAX          AirQualityEntry
MAX-ACCESS      not-accessible
STATUS          current
DESCRIPTION     "Entry in air quality table."
INDEX        { airQualityIndex }
::= { airQualityTable 1 }

AirQualityEntry ::= SEQUENCE {
airQualityIndex	    Unsigned32,
airQualityValue	    Unsigned32,
airQualityAlarm	    Unsigned32,
airQualityMax	    Unsigned32,
airQualityTimestamp	Integer32}

airQualityIndex OBJECT-TYPE
SYNTAX          Unsigned32
MAX-ACCESS      not-accessible
STATUS          current
DESCRIPTION     "Table Index."
::= { airQualityEntry 1}

airQualityValue OBJECT-TYPE
SYNTAX          Unsigned32
MAX-ACCESS      read-write
STATUS          current
DESCRIPTION     "Current value."
::= { airQualityEntry 2}

airQualityAlarm OBJECT-TYPE
SYNTAX          Unsigned32
MAX-ACCESS      read-write
STATUS          current
DESCRIPTION     "Current alarmstate."
::= { airQualityEntry 3}

airQualityMax OBJECT-TYPE
SYNTAX          Unsigned32
MAX-ACCESS      read-write
STATUS          current
DESCRIPTION     "Max. threshold of this value."
::= { airQualityEntry 5}

airQualityTimestamp OBJECT-TYPE
SYNTAX          Integer32
MAX-ACCESS      read-write
STATUS          current
DESCRIPTION     "Timestamp of alarmstate change."
::= { airQualityEntry 10}

-------------------------------------------------------------------------------------------
-- Sensor HeatDetection State
-------------------------------------------------------------------------------------------

heatDetectionTable OBJECT-TYPE
SYNTAX          SEQUENCE OF HeatDetectionEntry
MAX-ACCESS      not-accessible
STATUS          current
DESCRIPTION     "Heat detection states."
::= { sensors 18 }

heatDetectionEntry OBJECT-TYPE
SYNTAX          HeatDetectionEntry
MAX-ACCESS      not-accessible
STATUS          current
DESCRIPTION     "Entry in heat detection table."
INDEX        { heatDetectionIndex }
::= { heatDetectionTable 1 }

HeatDetectionEntry ::= SEQUENCE {
heatDetectionIndex	    Unsigned32,
heatDetectionValue	    Integer32,
heatDetectionAlarm	    Unsigned32,
heatDetectionMax	    Integer32,
heatDetectionTimestamp	Integer32}

heatDetectionIndex OBJECT-TYPE
SYNTAX          Unsigned32
MAX-ACCESS      not-accessible
STATUS          current
DESCRIPTION     "Table Index."
::= { heatDetectionEntry 1}

heatDetectionValue OBJECT-TYPE
SYNTAX          Integer32
MAX-ACCESS      read-write
STATUS          current
DESCRIPTION     "Current value."
::= { heatDetectionEntry 2}

heatDetectionAlarm OBJECT-TYPE
SYNTAX          Unsigned32
MAX-ACCESS      read-write
STATUS          current
DESCRIPTION     "Current alarmstate."
::= { heatDetectionEntry 3}

heatDetectionMax OBJECT-TYPE
SYNTAX          Integer32
MAX-ACCESS      read-write
STATUS          current
DESCRIPTION     "Max. threshold of this value."
::= { heatDetectionEntry 5}

heatDetectionTimestamp OBJECT-TYPE
SYNTAX          Integer32
MAX-ACCESS      read-write
STATUS          current
DESCRIPTION     "Timestamp of alarmstate change."
::= { heatDetectionEntry 10}

-------------------------------------------------------------------------------------------
-- Sensor AirQualityFire State
-------------------------------------------------------------------------------------------

airQualityFireTable OBJECT-TYPE
SYNTAX          SEQUENCE OF AirQualityFireEntry
MAX-ACCESS      not-accessible
STATUS          current
DESCRIPTION     "Air quality fire states."
::= { sensors 20 }

airQualityFireEntry OBJECT-TYPE
SYNTAX          AirQualityFireEntry
MAX-ACCESS      not-accessible
STATUS          current
DESCRIPTION     "Entry in air quality fire table."
INDEX        { airQualityFireIndex }
::= { airQualityFireTable 1 }

AirQualityFireEntry ::= SEQUENCE {
airQualityFireIndex	    Unsigned32,
airQualityFireValue	    Unsigned32,
airQualityFireAlarm	    Unsigned32,
airQualityFireMax	    Unsigned32,
airQualityFireTimestamp	Integer32}

airQualityFireIndex OBJECT-TYPE
SYNTAX          Unsigned32
MAX-ACCESS      not-accessible
STATUS          current
DESCRIPTION     "Table Index."
::= { airQualityFireEntry 1}

airQualityFireValue OBJECT-TYPE
SYNTAX          Unsigned32
MAX-ACCESS      read-write
STATUS          current
DESCRIPTION     "Current value."
::= { airQualityFireEntry 2}

airQualityFireAlarm OBJECT-TYPE
SYNTAX          Unsigned32
MAX-ACCESS      read-write
STATUS          current
DESCRIPTION     "Current alarmstate."
::= { airQualityFireEntry 3}

airQualityFireMax OBJECT-TYPE
SYNTAX          Unsigned32
MAX-ACCESS      read-write
STATUS          current
DESCRIPTION     "Max. threshold of this value."
::= { airQualityFireEntry 5}

airQualityFireTimestamp OBJECT-TYPE
SYNTAX          Integer32
MAX-ACCESS      read-write
STATUS          current
DESCRIPTION     "Timestamp of alarmstate change."
::= { airQualityFireEntry 10}

-------------------------------------------------------------------------------------------
-- Sensor co2
-------------------------------------------------------------------------------------------

co2Table OBJECT-TYPE
SYNTAX          SEQUENCE OF Co2Entry
MAX-ACCESS      not-accessible
STATUS          current
DESCRIPTION     "CO2 values."
::= { sensors 21 }

co2Entry OBJECT-TYPE
SYNTAX          Co2Entry
MAX-ACCESS      not-accessible
STATUS          current
DESCRIPTION     "Entry in co2 table."
INDEX        { co2Index }
::= { co2Table 1 }

Co2Entry ::= SEQUENCE {
co2Index			Unsigned32,
co2Value			Unsigned32,
co2Alarm			Unsigned32,
co2Max				Unsigned32,
co2Timestamp		Integer32}

co2Index OBJECT-TYPE
SYNTAX          Unsigned32
MAX-ACCESS      not-accessible
STATUS          current
DESCRIPTION     "Table Index."
::= { co2Entry 1}

co2Value OBJECT-TYPE
SYNTAX          Unsigned32
MAX-ACCESS      read-write
STATUS          current
DESCRIPTION     "Current value."
::= { co2Entry 2}

co2Alarm OBJECT-TYPE
SYNTAX          Unsigned32
MAX-ACCESS      read-write
STATUS          current
DESCRIPTION     "Current alarmstate."
::= { co2Entry 3}

co2Max OBJECT-TYPE
SYNTAX          Unsigned32
MAX-ACCESS      read-write
STATUS          current
DESCRIPTION     "Max. threshold of this value."
::= { co2Entry 5}

co2Timestamp OBJECT-TYPE
SYNTAX          Integer32
MAX-ACCESS      read-write
STATUS          current
DESCRIPTION     "Timestamp of alarmstate change."
::= { co2Entry 10}

-------------------------------------------------------------------------------------------
-- Sensor reed.
-------------------------------------------------------------------------------------------

reedTable OBJECT-TYPE
SYNTAX          SEQUENCE OF ReedEntry
MAX-ACCESS      not-accessible
STATUS          current
DESCRIPTION     "Reed values."
::= { sensors 22 }

reedEntry OBJECT-TYPE
SYNTAX          ReedEntry
MAX-ACCESS      not-accessible
STATUS          current
DESCRIPTION     "Entry in reed table."
INDEX        { reedIndex }
::= { reedTable 1 }

ReedEntry ::= SEQUENCE {
reedIndex	Unsigned32,
reedValue		Unsigned32,
reedAlarm		Unsigned32,
reedLogic		Unsigned32,
reedTimestamp	Integer32}

reedIndex OBJECT-TYPE
SYNTAX          Unsigned32
MAX-ACCESS      not-accessible
STATUS          current
DESCRIPTION     "Table Index."
::= { reedEntry 1}

reedValue OBJECT-TYPE
SYNTAX          Unsigned32
MAX-ACCESS      read-write
STATUS          current
DESCRIPTION     "Current value."
::= { reedEntry 2}

reedAlarm OBJECT-TYPE
SYNTAX          Unsigned32
MAX-ACCESS      read-write
STATUS          current
DESCRIPTION     "Current alarmstate."
::= { reedEntry 3}

reedLogic OBJECT-TYPE
SYNTAX          Unsigned32
MAX-ACCESS      read-write
STATUS          current
DESCRIPTION     "Logic of this value."
::= { reedEntry 5}

reedTimestamp OBJECT-TYPE
SYNTAX          Integer32
MAX-ACCESS      read-write
STATUS          current
DESCRIPTION     "Timestamp of alarmstate change."
::= { reedEntry 10}

-------------------------------------------------------------------------------------------
-- Sensor rcm ac
-------------------------------------------------------------------------------------------

rcmAcTable OBJECT-TYPE
SYNTAX          SEQUENCE OF RcmAcEntry
MAX-ACCESS      not-accessible
STATUS          current
DESCRIPTION     "SNMP retrieving values for the snmp monitoring."
::= { sensors 23 }

rcmAcEntry OBJECT-TYPE
SYNTAX          RcmAcEntry
MAX-ACCESS      not-accessible
STATUS          current
DESCRIPTION     "Entry in snmpValue table."
INDEX        { rcmAcIndex }
::= { rcmAcTable 1 }

RcmAcEntry ::= SEQUENCE {
rcmAcIndex		Unsigned32,
rcmAcValue		Integer32,
rcmAcAlarm		Unsigned32,
rcmAcMax		Integer32,
rcmAcTimestamp	Integer32}

rcmAcIndex OBJECT-TYPE
SYNTAX          Unsigned32
MAX-ACCESS      not-accessible
STATUS          current
DESCRIPTION     "Table Index."
::= { rcmAcEntry 1}

rcmAcValue OBJECT-TYPE
SYNTAX          Integer32
MAX-ACCESS      read-write
STATUS          current
DESCRIPTION     "Current value."
::= { rcmAcEntry 2}

rcmAcAlarm OBJECT-TYPE
SYNTAX          Unsigned32
MAX-ACCESS      read-write
STATUS          current
DESCRIPTION     "Current alarmstate."
::= { rcmAcEntry 3}

rcmAcMax OBJECT-TYPE
SYNTAX          Integer32
MAX-ACCESS      read-write
STATUS          current
DESCRIPTION     "Max. threshold of this value."
::= { rcmAcEntry 5}

rcmAcTimestamp OBJECT-TYPE
SYNTAX          Integer32
MAX-ACCESS      read-write
STATUS          current
DESCRIPTION     "Timestamp of alarmstate change."
::= { rcmAcEntry 10}

-------------------------------------------------------------------------------------------
-- Sensor rcm dc
-------------------------------------------------------------------------------------------

rcmDcTable OBJECT-TYPE
SYNTAX          SEQUENCE OF RcmDcEntry
MAX-ACCESS      not-accessible
STATUS          current
DESCRIPTION     "SNMP retrieving values for the snmp monitoring."
::= { sensors 24 }

rcmDcEntry OBJECT-TYPE
SYNTAX          RcmDcEntry
MAX-ACCESS      not-accessible
STATUS          current
DESCRIPTION     "Entry in snmpValue table."
INDEX        { rcmDcIndex }
::= { rcmDcTable 1 }

RcmDcEntry ::= SEQUENCE {
rcmDcIndex		Unsigned32,
rcmDcValue		Integer32,
rcmDcAlarm		Unsigned32,
rcmDcMax		Integer32,
rcmDcTimestamp	Integer32}

rcmDcIndex OBJECT-TYPE
SYNTAX          Unsigned32
MAX-ACCESS      not-accessible
STATUS          current
DESCRIPTION     "Table Index."
::= { rcmDcEntry 1}

rcmDcValue OBJECT-TYPE
SYNTAX          Integer32
MAX-ACCESS      read-write
STATUS          current
DESCRIPTION     "Current value."
::= { rcmDcEntry 2}

rcmDcAlarm OBJECT-TYPE
SYNTAX          Unsigned32
MAX-ACCESS      read-write
STATUS          current
DESCRIPTION     "Current alarmstate."
::= { rcmDcEntry 3}

rcmDcMax OBJECT-TYPE
SYNTAX          Integer32
MAX-ACCESS      read-write
STATUS          current
DESCRIPTION     "Max. threshold of this value."
::= { rcmDcEntry 5}

rcmDcTimestamp OBJECT-TYPE
SYNTAX          Integer32
MAX-ACCESS      read-write
STATUS          current
DESCRIPTION     "Timestamp of alarmstate change."
::= { rcmDcEntry 10}

-------------------------------------------------------------------------------------------
-- Sensor battery
-------------------------------------------------------------------------------------------

batteryTable OBJECT-TYPE
SYNTAX          SEQUENCE OF BatteryEntry
MAX-ACCESS      not-accessible
STATUS          current
DESCRIPTION     "SNMP retrieving values for the snmp monitoring."
::= { sensors 25 }

batteryEntry OBJECT-TYPE
SYNTAX          BatteryEntry
MAX-ACCESS      not-accessible
STATUS          current
DESCRIPTION     "Entry in snmpValue table."
INDEX        { batteryIndex }
::= { batteryTable 1 }

BatteryEntry ::= SEQUENCE {
batteryIndex		Unsigned32,
batteryValue		Integer32,
batteryAlarm		Unsigned32,
batteryTimestamp	Integer32}

batteryIndex OBJECT-TYPE
SYNTAX          Unsigned32
MAX-ACCESS      not-accessible
STATUS          current
DESCRIPTION     "Table Index."
::= { batteryEntry 1}

batteryValue OBJECT-TYPE
SYNTAX          Integer32
MAX-ACCESS      read-write
STATUS          current
DESCRIPTION     "Current value."
::= { batteryEntry 2}

batteryAlarm OBJECT-TYPE
SYNTAX          Unsigned32
MAX-ACCESS      read-write
STATUS          current
DESCRIPTION     "Current alarmstate."
::= { batteryEntry 3}

batteryTimestamp OBJECT-TYPE
SYNTAX          Integer32
MAX-ACCESS      read-write
STATUS          current
DESCRIPTION     "Timestamp of alarmstate change."
::= { batteryEntry 10}

-------------------------------------------------------------------------------------------
-- Sensor reed2.
-------------------------------------------------------------------------------------------

reed2Table OBJECT-TYPE
SYNTAX          SEQUENCE OF Reed2Entry
MAX-ACCESS      not-accessible
STATUS          current
DESCRIPTION     "Reed2 values."
::= { sensors 26 }

reed2Entry OBJECT-TYPE
SYNTAX          Reed2Entry
MAX-ACCESS      not-accessible
STATUS          current
DESCRIPTION     "Entry in reed2 table."
INDEX        { reed2Index }
::= { reed2Table 1 }

Reed2Entry ::= SEQUENCE {
reed2Index	Unsigned32,
reed2Value		Unsigned32,
reed2Alarm		Unsigned32,
reed2Logic		Unsigned32,
reed2Timestamp	Integer32}

reed2Index OBJECT-TYPE
SYNTAX          Unsigned32
MAX-ACCESS      not-accessible
STATUS          current
DESCRIPTION     "Table Index."
::= { reed2Entry 1}

reed2Value OBJECT-TYPE
SYNTAX          Unsigned32
MAX-ACCESS      read-write
STATUS          current
DESCRIPTION     "Current value."
::= { reed2Entry 2}

reed2Alarm OBJECT-TYPE
SYNTAX          Unsigned32
MAX-ACCESS      read-write
STATUS          current
DESCRIPTION     "Current alarmstate."
::= { reed2Entry 3}

reed2Logic OBJECT-TYPE
SYNTAX          Unsigned32
MAX-ACCESS      read-write
STATUS          current
DESCRIPTION     "Logic of this value."
::= { reed2Entry 5}

reed2Timestamp OBJECT-TYPE
SYNTAX          Integer32
MAX-ACCESS      read-write
STATUS          current
DESCRIPTION     "Timestamp of alarmstate change."
::= { reed2Entry 10}

-------------------------------------------------------------------------------------------
-- Sensor Tilt.
-------------------------------------------------------------------------------------------

tiltTable OBJECT-TYPE
SYNTAX          SEQUENCE OF TiltEntry
MAX-ACCESS      not-accessible
STATUS          current
DESCRIPTION     "Tilt values."
::= { sensors 27 }

tiltEntry OBJECT-TYPE
SYNTAX          TiltEntry
MAX-ACCESS      not-accessible
STATUS          current
DESCRIPTION     "Entry in tilt table."
INDEX        { tiltIndex }
::= { tiltTable 1 }

TiltEntry ::= SEQUENCE {
tiltIndex		Unsigned32,
tiltValue		Unsigned32,
tiltAlarm		Unsigned32,
tiltTimestamp	Integer32}

tiltIndex OBJECT-TYPE
SYNTAX          Unsigned32
MAX-ACCESS      not-accessible
STATUS          current
DESCRIPTION     "Table Index."
::= { tiltEntry 1}

tiltValue OBJECT-TYPE
SYNTAX          Unsigned32
MAX-ACCESS      read-write
STATUS          current
DESCRIPTION     "Current value."
::= { tiltEntry 2}

tiltAlarm OBJECT-TYPE
SYNTAX          Unsigned32
MAX-ACCESS      read-write
STATUS          current
DESCRIPTION     "Current alarmstate."
::= { tiltEntry 3}

tiltTimestamp OBJECT-TYPE
SYNTAX          Integer32
MAX-ACCESS      read-write
STATUS          current
DESCRIPTION     "Timestamp of alarmstate change."
::= { tiltEntry 10}

-------------------------------------------------------------------------------------------
-- Sensor inputs
-------------------------------------------------------------------------------------------

-------------------------------------------------------------------------------------------
-- Input 1.
-------------------------------------------------------------------------------------------

input1Table OBJECT-TYPE
SYNTAX          SEQUENCE OF Input1Entry
MAX-ACCESS      not-accessible
STATUS          current
DESCRIPTION     "Input1 values."
::= { inputs 1 }

input1Entry OBJECT-TYPE
SYNTAX          Input1Entry
MAX-ACCESS      not-accessible
STATUS          current
DESCRIPTION     "Entry in input1 table."
INDEX        { input1Index }
::= { input1Table 1 }

Input1Entry ::= SEQUENCE {
input1Index		Unsigned32,
input1Name		DisplayString,
input1Group		DisplayString,
input1Value		Integer32,
input1Alarm		Unsigned32,
input1Logic		Unsigned32,
input1Timestamp	Integer32}

input1Index OBJECT-TYPE
SYNTAX          Unsigned32
MAX-ACCESS      not-accessible
STATUS          current
DESCRIPTION     "Table Index."
::= { input1Entry 1}

input1Name OBJECT-TYPE
SYNTAX          DisplayString
MAX-ACCESS      read-write
STATUS          current
DESCRIPTION     "Name of the input."
::= { input1Entry 2}

input1Group OBJECT-TYPE
SYNTAX          DisplayString
MAX-ACCESS      read-write
STATUS          current
DESCRIPTION     "Alarmgroup of the input."
::= { input1Entry 3}

input1Value OBJECT-TYPE
SYNTAX          Integer32
MAX-ACCESS      read-write
STATUS          current
DESCRIPTION     "Current value of the input."
::= { input1Entry 4}

input1Alarm OBJECT-TYPE
SYNTAX          Unsigned32
MAX-ACCESS      read-write
STATUS          current
DESCRIPTION     "Current alarmstate of the input."
::= { input1Entry 5}

input1Logic OBJECT-TYPE
SYNTAX          Unsigned32
MAX-ACCESS      read-write
STATUS          current
DESCRIPTION     "Current logic of the input."
::= { input1Entry 6}

input1Timestamp OBJECT-TYPE
SYNTAX          Integer32
MAX-ACCESS      read-write
STATUS          current
DESCRIPTION     "Timestamp of alarmstate change."
::= { input1Entry 10}

-------------------------------------------------------------------------------------------
-- Input 2.
-------------------------------------------------------------------------------------------

input2Table OBJECT-TYPE
SYNTAX          SEQUENCE OF Input2Entry
MAX-ACCESS      not-accessible
STATUS          current
DESCRIPTION     "Input2 values."
::= { inputs 2 }

input2Entry OBJECT-TYPE
SYNTAX          Input2Entry
MAX-ACCESS      not-accessible
STATUS          current
DESCRIPTION     "Entry in input2 table."
INDEX        { input2Index }
::= { input2Table 1 }

Input2Entry ::= SEQUENCE {
input2Index		Unsigned32,
input2Name		DisplayString,
input2Group		DisplayString,
input2Value		Integer32,
input2Alarm		Unsigned32,
input2Logic		Unsigned32,
input2Timestamp	Integer32}

input2Index OBJECT-TYPE
SYNTAX          Unsigned32
MAX-ACCESS      not-accessible
STATUS          current
DESCRIPTION     "Table Index."
::= { input2Entry 1}

input2Name OBJECT-TYPE
SYNTAX          DisplayString
MAX-ACCESS      read-write
STATUS          current
DESCRIPTION     "Name of the input."
::= { input2Entry 2}

input2Group OBJECT-TYPE
SYNTAX          DisplayString
MAX-ACCESS      read-write
STATUS          current
DESCRIPTION     "Alarmgroup of the input."
::= { input2Entry 3}

input2Value OBJECT-TYPE
SYNTAX          Integer32
MAX-ACCESS      read-write
STATUS          current
DESCRIPTION     "Current value of the input."
::= { input2Entry 4}

input2Alarm OBJECT-TYPE
SYNTAX          Unsigned32
MAX-ACCESS      read-write
STATUS          current
DESCRIPTION     "Current alarmstate of the input."
::= { input2Entry 5}

input2Logic OBJECT-TYPE
SYNTAX          Unsigned32
MAX-ACCESS      read-write
STATUS          current
DESCRIPTION     "Current logic of the input."
::= { input2Entry 6}

input2Timestamp OBJECT-TYPE
SYNTAX          Integer32
MAX-ACCESS      read-write
STATUS          current
DESCRIPTION     "Timestamp of alarmstate change."
::= { input2Entry 10}

-------------------------------------------------------------------------------------------
-- Input 3.
-------------------------------------------------------------------------------------------

input3Table OBJECT-TYPE
SYNTAX          SEQUENCE OF Input3Entry
MAX-ACCESS      not-accessible
STATUS          current
DESCRIPTION     "Input3 values."
::= { inputs 3 }

input3Entry OBJECT-TYPE
SYNTAX          Input3Entry
MAX-ACCESS      not-accessible
STATUS          current
DESCRIPTION     "Entry in input3 table."
INDEX        { input3Index }
::= { input3Table 1 }

Input3Entry ::= SEQUENCE {
input3Index		Unsigned32,
input3Name		DisplayString,
input3Group		DisplayString,
input3Value		Integer32,
input3Alarm		Unsigned32,
input3Logic		Unsigned32,
input3Timestamp	Integer32}

input3Index OBJECT-TYPE
SYNTAX          Unsigned32
MAX-ACCESS      not-accessible
STATUS          current
DESCRIPTION     "Table Index."
::= { input3Entry 1}

input3Name OBJECT-TYPE
SYNTAX          DisplayString
MAX-ACCESS      read-write
STATUS          current
DESCRIPTION     "Name of the input."
::= { input3Entry 2}

input3Group OBJECT-TYPE
SYNTAX          DisplayString
MAX-ACCESS      read-write
STATUS          current
DESCRIPTION     "Alarmgroup of the input."
::= { input3Entry 3}

input3Value OBJECT-TYPE
SYNTAX          Integer32
MAX-ACCESS      read-write
STATUS          current
DESCRIPTION     "Current value of the input."
::= { input3Entry 4}

input3Alarm OBJECT-TYPE
SYNTAX          Unsigned32
MAX-ACCESS      read-write
STATUS          current
DESCRIPTION     "Current alarmstate of the input."
::= { input3Entry 5}

input3Logic OBJECT-TYPE
SYNTAX          Unsigned32
MAX-ACCESS      read-write
STATUS          current
DESCRIPTION     "Current logic of the input."
::= { input3Entry 6}

input3Timestamp OBJECT-TYPE
SYNTAX          Integer32
MAX-ACCESS      read-write
STATUS          current
DESCRIPTION     "Timestamp of alarmstate change."
::= { input3Entry 10}

-------------------------------------------------------------------------------------------
-- Input 4.
-------------------------------------------------------------------------------------------

input4Table OBJECT-TYPE
SYNTAX          SEQUENCE OF Input4Entry
MAX-ACCESS      not-accessible
STATUS          current
DESCRIPTION     "Input4 values."
::= { inputs 4 }

input4Entry OBJECT-TYPE
SYNTAX          Input4Entry
MAX-ACCESS      not-accessible
STATUS          current
DESCRIPTION     "Entry in input4 table."
INDEX        { input4Index }
::= { input4Table 1 }

Input4Entry ::= SEQUENCE {
input4Index		Unsigned32,
input4Name		DisplayString,
input4Group		DisplayString,
input4Value		Integer32,
input4Alarm		Unsigned32,
input4Logic		Unsigned32,
input4Timestamp	Integer32}

input4Index OBJECT-TYPE
SYNTAX          Unsigned32
MAX-ACCESS      not-accessible
STATUS          current
DESCRIPTION     "Table Index."
::= { input4Entry 1}

input4Name OBJECT-TYPE
SYNTAX          DisplayString
MAX-ACCESS      read-write
STATUS          current
DESCRIPTION     "Name of the input."
::= { input4Entry 2}

input4Group OBJECT-TYPE
SYNTAX          DisplayString
MAX-ACCESS      read-write
STATUS          current
DESCRIPTION     "Alarmgroup of the input."
::= { input4Entry 3}

input4Value OBJECT-TYPE
SYNTAX          Integer32
MAX-ACCESS      read-write
STATUS          current
DESCRIPTION     "Current value of the input."
::= { input4Entry 4}

input4Alarm OBJECT-TYPE
SYNTAX          Unsigned32
MAX-ACCESS      read-write
STATUS          current
DESCRIPTION     "Current alarmstate of the input."
::= { input4Entry 5}

input4Logic OBJECT-TYPE
SYNTAX          Unsigned32
MAX-ACCESS      read-write
STATUS          current
DESCRIPTION     "Current logic of the input."
::= { input4Entry 6}

input4Timestamp OBJECT-TYPE
SYNTAX          Integer32
MAX-ACCESS      read-write
STATUS          current
DESCRIPTION     "Timestamp of alarmstate change."
::= { input4Entry 10}

-------------------------------------------------------------------------------------------
-- Input 5.
-------------------------------------------------------------------------------------------

input5Table OBJECT-TYPE
SYNTAX          SEQUENCE OF Input5Entry
MAX-ACCESS      not-accessible
STATUS          current
DESCRIPTION     "Input5 values."
::= { inputs 5 }

input5Entry OBJECT-TYPE
SYNTAX          Input5Entry
MAX-ACCESS      not-accessible
STATUS          current
DESCRIPTION     "Entry in input5 table."
INDEX        { input5Index }
::= { input5Table 1 }

Input5Entry ::= SEQUENCE {
input5Index		Unsigned32,
input5Name		DisplayString,
input5Group		DisplayString,
input5Value		Integer32,
input5Alarm		Unsigned32,
input5Logic		Unsigned32,
input5Timestamp	Integer32}

input5Index OBJECT-TYPE
SYNTAX          Unsigned32
MAX-ACCESS      not-accessible
STATUS          current
DESCRIPTION     "Table Index."
::= { input5Entry 1}

input5Name OBJECT-TYPE
SYNTAX          DisplayString
MAX-ACCESS      read-write
STATUS          current
DESCRIPTION     "Name of the input."
::= { input5Entry 2}

input5Group OBJECT-TYPE
SYNTAX          DisplayString
MAX-ACCESS      read-write
STATUS          current
DESCRIPTION     "Alarmgroup of the input."
::= { input5Entry 3}

input5Value OBJECT-TYPE
SYNTAX          Integer32
MAX-ACCESS      read-write
STATUS          current
DESCRIPTION     "Current value of the input."
::= { input5Entry 4}

input5Alarm OBJECT-TYPE
SYNTAX          Unsigned32
MAX-ACCESS      read-write
STATUS          current
DESCRIPTION     "Current alarmstate of the input."
::= { input5Entry 5}

input5Logic OBJECT-TYPE
SYNTAX          Unsigned32
MAX-ACCESS      read-write
STATUS          current
DESCRIPTION     "Current logic of the input."
::= { input5Entry 6}

input5Timestamp OBJECT-TYPE
SYNTAX          Integer32
MAX-ACCESS      read-write
STATUS          current
DESCRIPTION     "Timestamp of alarmstate change."
::= { input5Entry 10}

-------------------------------------------------------------------------------------------
-- Input 6.
-------------------------------------------------------------------------------------------

input6Table OBJECT-TYPE
SYNTAX          SEQUENCE OF Input6Entry
MAX-ACCESS      not-accessible
STATUS          current
DESCRIPTION     "Input6 values."
::= { inputs 6 }

input6Entry OBJECT-TYPE
SYNTAX          Input6Entry
MAX-ACCESS      not-accessible
STATUS          current
DESCRIPTION     "Entry in input6 table."
INDEX        { input6Index }
::= { input6Table 1 }

Input6Entry ::= SEQUENCE {
input6Index		Unsigned32,
input6Name		DisplayString,
input6Group		DisplayString,
input6Value		Integer32,
input6Alarm		Unsigned32,
input6Logic		Unsigned32,
input6Timestamp	Integer32}

input6Index OBJECT-TYPE
SYNTAX          Unsigned32
MAX-ACCESS      not-accessible
STATUS          current
DESCRIPTION     "Table Index."
::= { input6Entry 1}

input6Name OBJECT-TYPE
SYNTAX          DisplayString
MAX-ACCESS      read-write
STATUS          current
DESCRIPTION     "Name of the input."
::= { input6Entry 2}

input6Group OBJECT-TYPE
SYNTAX          DisplayString
MAX-ACCESS      read-write
STATUS          current
DESCRIPTION     "Alarmgroup of the input."
::= { input6Entry 3}

input6Value OBJECT-TYPE
SYNTAX          Integer32
MAX-ACCESS      read-write
STATUS          current
DESCRIPTION     "Current value of the input."
::= { input6Entry 4}

input6Alarm OBJECT-TYPE
SYNTAX          Unsigned32
MAX-ACCESS      read-write
STATUS          current
DESCRIPTION     "Current alarmstate of the input."
::= { input6Entry 5}

input6Logic OBJECT-TYPE
SYNTAX          Unsigned32
MAX-ACCESS      read-write
STATUS          current
DESCRIPTION     "Current logic of the input."
::= { input6Entry 6}

input6Timestamp OBJECT-TYPE
SYNTAX          Integer32
MAX-ACCESS      read-write
STATUS          current
DESCRIPTION     "Timestamp of alarmstate change."
::= { input6Entry 10}

-------------------------------------------------------------------------------------------
-- Input 7.
-------------------------------------------------------------------------------------------

input7Table OBJECT-TYPE
SYNTAX          SEQUENCE OF Input7Entry
MAX-ACCESS      not-accessible
STATUS          current
DESCRIPTION     "Input7 values."
::= { inputs 7 }

input7Entry OBJECT-TYPE
SYNTAX          Input7Entry
MAX-ACCESS      not-accessible
STATUS          current
DESCRIPTION     "Entry in input7 table."
INDEX        { input7Index }
::= { input7Table 1 }

Input7Entry ::= SEQUENCE {
input7Index		Unsigned32,
input7Name		DisplayString,
input7Group		DisplayString,
input7Value		Integer32,
input7Alarm		Unsigned32,
input7Logic		Unsigned32,
input7Timestamp	Integer32}

input7Index OBJECT-TYPE
SYNTAX          Unsigned32
MAX-ACCESS      not-accessible
STATUS          current
DESCRIPTION     "Table Index."
::= { input7Entry 1}

input7Name OBJECT-TYPE
SYNTAX          DisplayString
MAX-ACCESS      read-write
STATUS          current
DESCRIPTION     "Name of the input."
::= { input7Entry 2}

input7Group OBJECT-TYPE
SYNTAX          DisplayString
MAX-ACCESS      read-write
STATUS          current
DESCRIPTION     "Alarmgroup of the input."
::= { input7Entry 3}

input7Value OBJECT-TYPE
SYNTAX          Integer32
MAX-ACCESS      read-write
STATUS          current
DESCRIPTION     "Current value of the input."
::= { input7Entry 4}

input7Alarm OBJECT-TYPE
SYNTAX          Unsigned32
MAX-ACCESS      read-write
STATUS          current
DESCRIPTION     "Current alarmstate of the input."
::= { input7Entry 5}

input7Logic OBJECT-TYPE
SYNTAX          Unsigned32
MAX-ACCESS      read-write
STATUS          current
DESCRIPTION     "Current logic of the input."
::= { input7Entry 6}

input7Timestamp OBJECT-TYPE
SYNTAX          Integer32
MAX-ACCESS      read-write
STATUS          current
DESCRIPTION     "Timestamp of alarmstate change."
::= { input7Entry 10}

-------------------------------------------------------------------------------------------
-- Input 8.
-------------------------------------------------------------------------------------------

input8Table OBJECT-TYPE
SYNTAX          SEQUENCE OF Input8Entry
MAX-ACCESS      not-accessible
STATUS          current
DESCRIPTION     "Input8 values."
::= { inputs 8 }

input8Entry OBJECT-TYPE
SYNTAX          Input8Entry
MAX-ACCESS      not-accessible
STATUS          current
DESCRIPTION     "Entry in input8 table."
INDEX        { input8Index }
::= { input8Table 1 }

Input8Entry ::= SEQUENCE {
input8Index		Unsigned32,
input8Name		DisplayString,
input8Group		DisplayString,
input8Value		Integer32,
input8Alarm		Unsigned32,
input8Logic		Unsigned32,
input8Timestamp	Integer32}

input8Index OBJECT-TYPE
SYNTAX          Unsigned32
MAX-ACCESS      not-accessible
STATUS          current
DESCRIPTION     "Table Index."
::= { input8Entry 1}

input8Name OBJECT-TYPE
SYNTAX          DisplayString
MAX-ACCESS      read-write
STATUS          current
DESCRIPTION     "Name of the input."
::= { input8Entry 2}

input8Group OBJECT-TYPE
SYNTAX          DisplayString
MAX-ACCESS      read-write
STATUS          current
DESCRIPTION     "Alarmgroup of the input."
::= { input8Entry 3}

input8Value OBJECT-TYPE
SYNTAX          Integer32
MAX-ACCESS      read-write
STATUS          current
DESCRIPTION     "Current value of the input."
::= { input8Entry 4}

input8Alarm OBJECT-TYPE
SYNTAX          Unsigned32
MAX-ACCESS      read-write
STATUS          current
DESCRIPTION     "Current alarmstate of the input."
::= { input8Entry 5}

input8Logic OBJECT-TYPE
SYNTAX          Unsigned32
MAX-ACCESS      read-write
STATUS          current
DESCRIPTION     "Current logic of the input."
::= { input8Entry 6}

input8Timestamp OBJECT-TYPE
SYNTAX          Integer32
MAX-ACCESS      read-write
STATUS          current
DESCRIPTION     "Timestamp of alarmstate change."
::= { input8Entry 10}

-------------------------------------------------------------------------------------------
-- Input 9.
-------------------------------------------------------------------------------------------

input9Table OBJECT-TYPE
SYNTAX          SEQUENCE OF Input9Entry
MAX-ACCESS      not-accessible
STATUS          current
DESCRIPTION     "Input9 values."
::= { inputs 9 }

input9Entry OBJECT-TYPE
SYNTAX          Input9Entry
MAX-ACCESS      not-accessible
STATUS          current
DESCRIPTION     "Entry in input9 table."
INDEX        { input9Index }
::= { input9Table 1 }

Input9Entry ::= SEQUENCE {
input9Index		Unsigned32,
input9Name		DisplayString,
input9Group		DisplayString,
input9Value		Integer32,
input9Alarm		Unsigned32,
input9Logic		Unsigned32,
input9Timestamp	Integer32}

input9Index OBJECT-TYPE
SYNTAX          Unsigned32
MAX-ACCESS      not-accessible
STATUS          current
DESCRIPTION     "Table Index."
::= { input9Entry 1}

input9Name OBJECT-TYPE
SYNTAX          DisplayString
MAX-ACCESS      read-write
STATUS          current
DESCRIPTION     "Name of the input."
::= { input9Entry 2}

input9Group OBJECT-TYPE
SYNTAX          DisplayString
MAX-ACCESS      read-write
STATUS          current
DESCRIPTION     "Alarmgroup of the input."
::= { input9Entry 3}

input9Value OBJECT-TYPE
SYNTAX          Integer32
MAX-ACCESS      read-write
STATUS          current
DESCRIPTION     "Current value of the input."
::= { input9Entry 4}

input9Alarm OBJECT-TYPE
SYNTAX          Unsigned32
MAX-ACCESS      read-write
STATUS          current
DESCRIPTION     "Current alarmstate of the input."
::= { input9Entry 5}

input9Logic OBJECT-TYPE
SYNTAX          Unsigned32
MAX-ACCESS      read-write
STATUS          current
DESCRIPTION     "Current logic of the input."
::= { input9Entry 6}

input9Timestamp OBJECT-TYPE
SYNTAX          Integer32
MAX-ACCESS      read-write
STATUS          current
DESCRIPTION     "Timestamp of alarmstate change."
::= { input9Entry 10}

-------------------------------------------------------------------------------------------
-- Input 10.
-------------------------------------------------------------------------------------------

input10Table OBJECT-TYPE
SYNTAX          SEQUENCE OF Input10Entry
MAX-ACCESS      not-accessible
STATUS          current
DESCRIPTION     "Input10 values."
::= { inputs 10 }

input10Entry OBJECT-TYPE
SYNTAX          Input10Entry
MAX-ACCESS      not-accessible
STATUS          current
DESCRIPTION     "Entry in input10 table."
INDEX        { input10Index }
::= { input10Table 1 }

Input10Entry ::= SEQUENCE {
input10Index		Unsigned32,
input10Name			DisplayString,
input10Group		DisplayString,
input10Value		Integer32,
input10Alarm		Unsigned32,
input10Logic        Unsigned32,
input10Timestamp	Integer32}

input10Index OBJECT-TYPE
SYNTAX          Unsigned32
MAX-ACCESS      not-accessible
STATUS          current
DESCRIPTION     "Table Index."
::= { input10Entry 1}

input10Name OBJECT-TYPE
SYNTAX          DisplayString
MAX-ACCESS      read-write
STATUS          current
DESCRIPTION     "Name of the input."
::= { input10Entry 2}

input10Group OBJECT-TYPE
SYNTAX          DisplayString
MAX-ACCESS      read-write
STATUS          current
DESCRIPTION     "Alarmgroup of the input."
::= { input10Entry 3}

input10Value OBJECT-TYPE
SYNTAX          Integer32
MAX-ACCESS      read-write
STATUS          current
DESCRIPTION     "Current value of the input."
::= { input10Entry 4}

input10Alarm OBJECT-TYPE
SYNTAX          Unsigned32
MAX-ACCESS      read-write
STATUS          current
DESCRIPTION     "Current alarmstate of the input."
::= { input10Entry 5}

input10Logic OBJECT-TYPE
SYNTAX          Unsigned32
MAX-ACCESS      read-write
STATUS          current
DESCRIPTION     "Current logic of the input."
::= { input10Entry 6}

input10Timestamp OBJECT-TYPE
SYNTAX          Integer32
MAX-ACCESS      read-write
STATUS          current
DESCRIPTION     "Timestamp of alarmstate change."
::= { input10Entry 10}

-------------------------------------------------------------------------------------------
-- Input 11.
-------------------------------------------------------------------------------------------

input11Table OBJECT-TYPE
SYNTAX          SEQUENCE OF Input11Entry
MAX-ACCESS      not-accessible
STATUS          current
DESCRIPTION     "Input11 values."
::= { inputs 11 }

input11Entry OBJECT-TYPE
SYNTAX          Input11Entry
MAX-ACCESS      not-accessible
STATUS          current
DESCRIPTION     "Entry in input11 table."
INDEX        { input11Index }
::= { input11Table 1 }

Input11Entry ::= SEQUENCE {
input11Index		Unsigned32,
input11Name			DisplayString,
input11Group		DisplayString,
input11Value		Integer32,
input11Alarm		Unsigned32,
input11Logic		Unsigned32,
input11Timestamp	Integer32}

input11Index OBJECT-TYPE
SYNTAX          Unsigned32
MAX-ACCESS      not-accessible
STATUS          current
DESCRIPTION     "Table Index."
::= { input11Entry 1}

input11Name OBJECT-TYPE
SYNTAX          DisplayString
MAX-ACCESS      read-write
STATUS          current
DESCRIPTION     "Name of the input."
::= { input11Entry 2}

input11Group OBJECT-TYPE
SYNTAX          DisplayString
MAX-ACCESS      read-write
STATUS          current
DESCRIPTION     "Alarmgroup of the input."
::= { input11Entry 3}

input11Value OBJECT-TYPE
SYNTAX          Integer32
MAX-ACCESS      read-write
STATUS          current
DESCRIPTION     "Current value of the input."
::= { input11Entry 4}

input11Alarm OBJECT-TYPE
SYNTAX          Unsigned32
MAX-ACCESS      read-write
STATUS          current
DESCRIPTION     "Current alarmstate of the input."
::= { input11Entry 5}

input11Logic OBJECT-TYPE
SYNTAX          Unsigned32
MAX-ACCESS      read-write
STATUS          current
DESCRIPTION     "Current logic of the input."
::= { input11Entry 6}

input11Timestamp OBJECT-TYPE
SYNTAX          Integer32
MAX-ACCESS      read-write
STATUS          current
DESCRIPTION     "Timestamp of alarmstate change."
::= { input11Entry 10}

-------------------------------------------------------------------------------------------
-- Input 12.
-------------------------------------------------------------------------------------------

input12Table OBJECT-TYPE
SYNTAX          SEQUENCE OF Input12Entry
MAX-ACCESS      not-accessible
STATUS          current
DESCRIPTION     "Input12 values."
::= { inputs 12 }

input12Entry OBJECT-TYPE
SYNTAX          Input12Entry
MAX-ACCESS      not-accessible
STATUS          current
DESCRIPTION     "Entry in input12 table."
INDEX        { input12Index }
::= { input12Table 1 }

Input12Entry ::= SEQUENCE {
input12Index		Unsigned32,
input12Name			DisplayString,
input12Group		DisplayString,
input12Value		Integer32,
input12Alarm		Unsigned32,
input12Logic		Unsigned32,
input12Timestamp	Integer32}

input12Index OBJECT-TYPE
SYNTAX          Unsigned32
MAX-ACCESS      not-accessible
STATUS          current
DESCRIPTION     "Table Index."
::= { input12Entry 1}

input12Name OBJECT-TYPE
SYNTAX          DisplayString
MAX-ACCESS      read-write
STATUS          current
DESCRIPTION     "Name of the input."
::= { input12Entry 2}

input12Group OBJECT-TYPE
SYNTAX          DisplayString
MAX-ACCESS      read-write
STATUS          current
DESCRIPTION     "Alarmgroup of the input."
::= { input12Entry 3}

input12Value OBJECT-TYPE
SYNTAX          Integer32
MAX-ACCESS      read-write
STATUS          current
DESCRIPTION     "Current value of the input."
::= { input12Entry 4}

input12Alarm OBJECT-TYPE
SYNTAX          Unsigned32
MAX-ACCESS      read-write
STATUS          current
DESCRIPTION     "Current alarmstate of the input."
::= { input12Entry 5}

input12Logic OBJECT-TYPE
SYNTAX          Unsigned32
MAX-ACCESS      read-write
STATUS          current
DESCRIPTION     "Current logic of the input."
::= { input12Entry 6}

input12Timestamp OBJECT-TYPE
SYNTAX          Integer32
MAX-ACCESS      read-write
STATUS          current
DESCRIPTION     "Timestamp of alarmstate change."
::= { input12Entry 10}

-------------------------------------------------------------------------------------------
-- Input 13.
-------------------------------------------------------------------------------------------

input13Table OBJECT-TYPE
SYNTAX          SEQUENCE OF Input13Entry
MAX-ACCESS      not-accessible
STATUS          current
DESCRIPTION     "Input13 values."
::= { inputs 13 }

input13Entry OBJECT-TYPE
SYNTAX          Input13Entry
MAX-ACCESS      not-accessible
STATUS          current
DESCRIPTION     "Entry in input13 table."
INDEX        { input13Index }
::= { input13Table 1 }

Input13Entry ::= SEQUENCE {
input13Index		Unsigned32,
input13Name			DisplayString,
input13Group		DisplayString,
input13Value		Integer32,
input13Alarm		Unsigned32,
input13Logic		Unsigned32,
input13Timestamp	Integer32}

input13Index OBJECT-TYPE
SYNTAX          Unsigned32
MAX-ACCESS      not-accessible
STATUS          current
DESCRIPTION     "Table Index."
::= { input13Entry 1}

input13Name OBJECT-TYPE
SYNTAX          DisplayString
MAX-ACCESS      read-write
STATUS          current
DESCRIPTION     "Name of the input."
::= { input13Entry 2}

input13Group OBJECT-TYPE
SYNTAX          DisplayString
MAX-ACCESS      read-write
STATUS          current
DESCRIPTION     "Alarmgroup of the input."
::= { input13Entry 3}

input13Value OBJECT-TYPE
SYNTAX          Integer32
MAX-ACCESS      read-write
STATUS          current
DESCRIPTION     "Current value of the input."
::= { input13Entry 4}

input13Alarm OBJECT-TYPE
SYNTAX          Unsigned32
MAX-ACCESS      read-write
STATUS          current
DESCRIPTION     "Current alarmstate of the input."
::= { input13Entry 5}

input13Logic OBJECT-TYPE
SYNTAX          Unsigned32
MAX-ACCESS      read-write
STATUS          current
DESCRIPTION     "Current logic of the input."
::= { input13Entry 6}

input13Timestamp OBJECT-TYPE
SYNTAX          Integer32
MAX-ACCESS      read-write
STATUS          current
DESCRIPTION     "Timestamp of alarmstate change."
::= { input13Entry 10}

-------------------------------------------------------------------------------------------
-- Input 14.
-------------------------------------------------------------------------------------------

input14Table OBJECT-TYPE
SYNTAX          SEQUENCE OF Input14Entry
MAX-ACCESS      not-accessible
STATUS          current
DESCRIPTION     "Input14 values."
::= { inputs 14 }

input14Entry OBJECT-TYPE
SYNTAX          Input14Entry
MAX-ACCESS      not-accessible
STATUS          current
DESCRIPTION     "Entry in input14 table."
INDEX        { input14Index }
::= { input14Table 1 }

Input14Entry ::= SEQUENCE {
input14Index		Unsigned32,
input14Name			DisplayString,
input14Group		DisplayString,
input14Value		Integer32,
input14Alarm		Unsigned32,
input14Logic		Unsigned32,
input14Timestamp	Integer32}

input14Index OBJECT-TYPE
SYNTAX          Unsigned32
MAX-ACCESS      not-accessible
STATUS          current
DESCRIPTION     "Table Index."
::= { input14Entry 1}

input14Name OBJECT-TYPE
SYNTAX          DisplayString
MAX-ACCESS      read-write
STATUS          current
DESCRIPTION     "Name of the input."
::= { input14Entry 2}

input14Group OBJECT-TYPE
SYNTAX          DisplayString
MAX-ACCESS      read-write
STATUS          current
DESCRIPTION     "Alarmgroup of the input."
::= { input14Entry 3}

input14Value OBJECT-TYPE
SYNTAX          Integer32
MAX-ACCESS      read-write
STATUS          current
DESCRIPTION     "Current value of the input."
::= { input14Entry 4}

input14Alarm OBJECT-TYPE
SYNTAX          Unsigned32
MAX-ACCESS      read-write
STATUS          current
DESCRIPTION     "Current alarmstate of the input."
::= { input14Entry 5}

input14Logic OBJECT-TYPE
SYNTAX          Unsigned32
MAX-ACCESS      read-write
STATUS          current
DESCRIPTION     "Current logic of the input."
::= { input14Entry 6}

input14Timestamp OBJECT-TYPE
SYNTAX          Integer32
MAX-ACCESS      read-write
STATUS          current
DESCRIPTION     "Timestamp of alarmstate change."
::= { input14Entry 10}

-------------------------------------------------------------------------------------------
-- Input 15.
-------------------------------------------------------------------------------------------

input15Table OBJECT-TYPE
SYNTAX          SEQUENCE OF Input15Entry
MAX-ACCESS      not-accessible
STATUS          current
DESCRIPTION     "Input15 values."
::= { inputs 15 }

input15Entry OBJECT-TYPE
SYNTAX          Input15Entry
MAX-ACCESS      not-accessible
STATUS          current
DESCRIPTION     "Entry in input15 table."
INDEX        { input15Index }
::= { input15Table 1 }

Input15Entry ::= SEQUENCE {
input15Index		Unsigned32,
input15Name			DisplayString,
input15Group		DisplayString,
input15Value		Integer32,
input15Alarm		Unsigned32,
input15Logic		Unsigned32,
input15Timestamp	Integer32}

input15Index OBJECT-TYPE
SYNTAX          Unsigned32
MAX-ACCESS      not-accessible
STATUS          current
DESCRIPTION     "Table Index."
::= { input15Entry 1}

input15Name OBJECT-TYPE
SYNTAX          DisplayString
MAX-ACCESS      read-write
STATUS          current
DESCRIPTION     "Name of the input."
::= { input15Entry 2}

input15Group OBJECT-TYPE
SYNTAX          DisplayString
MAX-ACCESS      read-write
STATUS          current
DESCRIPTION     "Alarmgroup of the input."
::= { input15Entry 3}

input15Value OBJECT-TYPE
SYNTAX          Integer32
MAX-ACCESS      read-write
STATUS          current
DESCRIPTION     "Current value of the input."
::= { input15Entry 4}

input15Alarm OBJECT-TYPE
SYNTAX          Unsigned32
MAX-ACCESS      read-write
STATUS          current
DESCRIPTION     "Current alarmstate of the input."
::= { input15Entry 5}

input15Logic OBJECT-TYPE
SYNTAX          Unsigned32
MAX-ACCESS      read-write
STATUS          current
DESCRIPTION     "Current logic of the input."
::= { input15Entry 6}

input15Timestamp OBJECT-TYPE
SYNTAX          Integer32
MAX-ACCESS      read-write
STATUS          current
DESCRIPTION     "Timestamp of alarmstate change."
::= { input15Entry 10}

-------------------------------------------------------------------------------------------
-- Input 16.
-------------------------------------------------------------------------------------------

input16Table OBJECT-TYPE
SYNTAX          SEQUENCE OF Input16Entry
MAX-ACCESS      not-accessible
STATUS          current
DESCRIPTION     "Input16 values."
::= { inputs 16 }

input16Entry OBJECT-TYPE
SYNTAX          Input16Entry
MAX-ACCESS      not-accessible
STATUS          current
DESCRIPTION     "Entry in input16 table."
INDEX        { input16Index }
::= { input16Table 1 }

Input16Entry ::= SEQUENCE {
input16Index		Unsigned32,
input16Name			DisplayString,
input16Group		DisplayString,
input16Value		Integer32,
input16Alarm		Unsigned32,
input16Logic		Unsigned32,
input16Timestamp	Integer32}

input16Index OBJECT-TYPE
SYNTAX          Unsigned32
MAX-ACCESS      not-accessible
STATUS          current
DESCRIPTION     "Table Index."
::= { input16Entry 1}

input16Name OBJECT-TYPE
SYNTAX          DisplayString
MAX-ACCESS      read-write
STATUS          current
DESCRIPTION     "Name of the input."
::= { input16Entry 2}

input16Group OBJECT-TYPE
SYNTAX          DisplayString
MAX-ACCESS      read-write
STATUS          current
DESCRIPTION     "Alarmgroup of the input."
::= { input16Entry 3}

input16Value OBJECT-TYPE
SYNTAX          Integer32
MAX-ACCESS      read-write
STATUS          current
DESCRIPTION     "Current value of the input."
::= { input16Entry 4}

input16Alarm OBJECT-TYPE
SYNTAX          Unsigned32
MAX-ACCESS      read-write
STATUS          current
DESCRIPTION     "Current alarmstate of the input."
::= { input16Entry 5}

input16Logic OBJECT-TYPE
SYNTAX          Unsigned32
MAX-ACCESS      read-write
STATUS          current
DESCRIPTION     "Current logic of the input."
::= { input16Entry 6}

input16Timestamp OBJECT-TYPE
SYNTAX          Integer32
MAX-ACCESS      read-write
STATUS          current
DESCRIPTION     "Timestamp of alarmstate change."
::= { input16Entry 10}

-------------------------------------------------------------------------------------------
-- Sensor outputs
-------------------------------------------------------------------------------------------

-------------------------------------------------------------------------------------------
-- Output 1.
-------------------------------------------------------------------------------------------

output1Table OBJECT-TYPE
SYNTAX          SEQUENCE OF Output1Entry
MAX-ACCESS      not-accessible
STATUS          current
DESCRIPTION     "Output1 values."
::= { outputs 1 }

output1Entry OBJECT-TYPE
SYNTAX          Output1Entry
MAX-ACCESS      not-accessible
STATUS          current
DESCRIPTION     "Entry in output1 table."
INDEX        { output1Index }
::= { output1Table 1 }

Output1Entry ::= SEQUENCE {
output1Index	Unsigned32,
output1Name     DisplayString,
output1Value	TruthValue}

output1Index OBJECT-TYPE
SYNTAX          Unsigned32
MAX-ACCESS      not-accessible
STATUS          current
DESCRIPTION     "Table Index."
::= { output1Entry 1}

output1Name OBJECT-TYPE
SYNTAX          DisplayString
MAX-ACCESS      read-write
STATUS          current
DESCRIPTION     "Name of the output."
::= { output1Entry 2}

output1Value OBJECT-TYPE
SYNTAX          TruthValue
MAX-ACCESS      read-write
STATUS          current
DESCRIPTION     "Current value of the output."
::= { output1Entry 3}


-------------------------------------------------------------------------------------------
-- Output 2.
-------------------------------------------------------------------------------------------

output2Table OBJECT-TYPE
SYNTAX          SEQUENCE OF Output2Entry
MAX-ACCESS      not-accessible
STATUS          current
DESCRIPTION     "Output2 values."
::= { outputs 2 }

output2Entry OBJECT-TYPE
SYNTAX          Output2Entry
MAX-ACCESS      not-accessible
STATUS          current
DESCRIPTION     "Entry in output2 table."
INDEX        { output2Index }
::= { output2Table 1 }

Output2Entry ::= SEQUENCE {
output2Index	Unsigned32,
output2Name	DisplayString,
output2Value	TruthValue}

output2Index OBJECT-TYPE
SYNTAX          Unsigned32
MAX-ACCESS      not-accessible
STATUS          current
DESCRIPTION     "Table Index."
::= { output2Entry 1}

output2Name OBJECT-TYPE
SYNTAX          DisplayString
MAX-ACCESS      read-write
STATUS          current
DESCRIPTION     "Name of the output."
::= { output2Entry 2}

output2Value OBJECT-TYPE
SYNTAX          TruthValue
MAX-ACCESS      read-write
STATUS          current
DESCRIPTION     "Current value of the output."
::= { output2Entry 3}


-------------------------------------------------------------------------------------------
-- Output 3.
-------------------------------------------------------------------------------------------

output3Table OBJECT-TYPE
SYNTAX          SEQUENCE OF Output3Entry
MAX-ACCESS      not-accessible
STATUS          current
DESCRIPTION     "Output3 values."
::= { outputs 3 }

output3Entry OBJECT-TYPE
SYNTAX          Output3Entry
MAX-ACCESS      not-accessible
STATUS          current
DESCRIPTION     "Entry in output3 table."
INDEX        { output3Index }
::= { output3Table 1 }

Output3Entry ::= SEQUENCE {
output3Index	Unsigned32,
output3Name	DisplayString,
output3Value	TruthValue}

output3Index OBJECT-TYPE
SYNTAX          Unsigned32
MAX-ACCESS      not-accessible
STATUS          current
DESCRIPTION     "Table Index."
::= { output3Entry 1}

output3Name OBJECT-TYPE
SYNTAX          DisplayString
MAX-ACCESS      read-write
STATUS          current
DESCRIPTION     "Name of the output."
::= { output3Entry 2}

output3Value OBJECT-TYPE
SYNTAX          TruthValue
MAX-ACCESS      read-write
STATUS          current
DESCRIPTION     "Current value of the output."
::= { output3Entry 3}


-------------------------------------------------------------------------------------------
-- Output 4.
-------------------------------------------------------------------------------------------

output4Table OBJECT-TYPE
SYNTAX          SEQUENCE OF Output4Entry
MAX-ACCESS      not-accessible
STATUS          current
DESCRIPTION     "Output4 values."
::= { outputs 4 }

output4Entry OBJECT-TYPE
SYNTAX          Output4Entry
MAX-ACCESS      not-accessible
STATUS          current
DESCRIPTION     "Entry in output4 table."
INDEX        { output4Index }
::= { output4Table 1 }

Output4Entry ::= SEQUENCE {
output4Index	Unsigned32,
output4Name	DisplayString,
output4Value	TruthValue}

output4Index OBJECT-TYPE
SYNTAX          Unsigned32
MAX-ACCESS      not-accessible
STATUS          current
DESCRIPTION     "Table Index."
::= { output4Entry 1}

output4Name OBJECT-TYPE
SYNTAX          DisplayString
MAX-ACCESS      read-write
STATUS          current
DESCRIPTION     "Name of the output."
::= { output4Entry 2}

output4Value OBJECT-TYPE
SYNTAX          TruthValue
MAX-ACCESS      read-write
STATUS          current
DESCRIPTION     "Current value of the output."
::= { output4Entry 3}


-------------------------------------------------------------------------------------------
-- Output 5.
-------------------------------------------------------------------------------------------

output5Table OBJECT-TYPE
SYNTAX          SEQUENCE OF Output5Entry
MAX-ACCESS      not-accessible
STATUS          current
DESCRIPTION     "Output5 values."
::= { outputs 5 }

output5Entry OBJECT-TYPE
SYNTAX          Output5Entry
MAX-ACCESS      not-accessible
STATUS          current
DESCRIPTION     "Entry in output5 table."
INDEX        { output5Index }
::= { output5Table 1 }

Output5Entry ::= SEQUENCE {
output5Index	Unsigned32,
output5Name	DisplayString,
output5Value	TruthValue}

output5Index OBJECT-TYPE
SYNTAX          Unsigned32
MAX-ACCESS      not-accessible
STATUS          current
DESCRIPTION     "Table Index."
::= { output5Entry 1}

output5Name OBJECT-TYPE
SYNTAX          DisplayString
MAX-ACCESS      read-write
STATUS          current
DESCRIPTION     "Name of the output."
::= { output5Entry 2}

output5Value OBJECT-TYPE
SYNTAX          TruthValue
MAX-ACCESS      read-write
STATUS          current
DESCRIPTION     "Current value of the output."
::= { output5Entry 3}


-------------------------------------------------------------------------------------------
-- Output 6.
-------------------------------------------------------------------------------------------

output6Table OBJECT-TYPE
SYNTAX          SEQUENCE OF Output6Entry
MAX-ACCESS      not-accessible
STATUS          current
DESCRIPTION     "Output6 values."
::= { outputs 6 }

output6Entry OBJECT-TYPE
SYNTAX          Output6Entry
MAX-ACCESS      not-accessible
STATUS          current
DESCRIPTION     "Entry in output6 table."
INDEX        { output6Index }
::= { output6Table 1 }

Output6Entry ::= SEQUENCE {
output6Index	Unsigned32,
output6Name	DisplayString,
output6Value	TruthValue}

output6Index OBJECT-TYPE
SYNTAX          Unsigned32
MAX-ACCESS      not-accessible
STATUS          current
DESCRIPTION     "Table Index."
::= { output6Entry 1}

output6Name OBJECT-TYPE
SYNTAX          DisplayString
MAX-ACCESS      read-write
STATUS          current
DESCRIPTION     "Name of the output."
::= { output6Entry 2}

output6Value OBJECT-TYPE
SYNTAX          TruthValue
MAX-ACCESS      read-write
STATUS          current
DESCRIPTION     "Current value of the output."
::= { output6Entry 3}


-------------------------------------------------------------------------------------------
-- Output 7.
-------------------------------------------------------------------------------------------

output7Table OBJECT-TYPE
SYNTAX          SEQUENCE OF Output7Entry
MAX-ACCESS      not-accessible
STATUS          current
DESCRIPTION     "Output7 values."
::= { outputs 7 }

output7Entry OBJECT-TYPE
SYNTAX          Output7Entry
MAX-ACCESS      not-accessible
STATUS          current
DESCRIPTION     "Entry in output7 table."
INDEX        { output7Index }
::= { output7Table 1 }

Output7Entry ::= SEQUENCE {
output7Index	Unsigned32,
output7Name	DisplayString,
output7Value	TruthValue}

output7Index OBJECT-TYPE
SYNTAX          Unsigned32
MAX-ACCESS      not-accessible
STATUS          current
DESCRIPTION     "Table Index."
::= { output7Entry 1}

output7Name OBJECT-TYPE
SYNTAX          DisplayString
MAX-ACCESS      read-write
STATUS          current
DESCRIPTION     "Name of the output."
::= { output7Entry 2}

output7Value OBJECT-TYPE
SYNTAX          TruthValue
MAX-ACCESS      read-write
STATUS          current
DESCRIPTION     "Current value of the output."
::= { output7Entry 3}


-------------------------------------------------------------------------------------------
-- Output 8.
-------------------------------------------------------------------------------------------

output8Table OBJECT-TYPE
SYNTAX          SEQUENCE OF Output8Entry
MAX-ACCESS      not-accessible
STATUS          current
DESCRIPTION     "Output8 values."
::= { outputs 8 }

output8Entry OBJECT-TYPE
SYNTAX          Output8Entry
MAX-ACCESS      not-accessible
STATUS          current
DESCRIPTION     "Entry in output8 table."
INDEX        { output8Index }
::= { output8Table 1 }

Output8Entry ::= SEQUENCE {
output8Index	Unsigned32,
output8Name	DisplayString,
output8Value	TruthValue}

output8Index OBJECT-TYPE
SYNTAX          Unsigned32
MAX-ACCESS      not-accessible
STATUS          current
DESCRIPTION     "Table Index."
::= { output8Entry 1}

output8Name OBJECT-TYPE
SYNTAX          DisplayString
MAX-ACCESS      read-write
STATUS          current
DESCRIPTION     "Name of the output."
::= { output8Entry 2}

output8Value OBJECT-TYPE
SYNTAX          TruthValue
MAX-ACCESS      read-write
STATUS          current
DESCRIPTION     "Current value of the output."
::= { output8Entry 3}

-------------------------------------------------------------------------------------------
-- Sensor phases
-------------------------------------------------------------------------------------------

-------------------------------------------------------------------------------------------
-- Sensor phase1
-------------------------------------------------------------------------------------------

-------------------------------------------------------------------------------------------
-- phase1 General
-------------------------------------------------------------------------------------------

phase1GeneralTable OBJECT-TYPE
SYNTAX          SEQUENCE OF Phase1GeneralEntry
MAX-ACCESS      not-accessible
STATUS          current
DESCRIPTION     "Phase1General values."
::= { phase1 1 }

phase1GeneralEntry OBJECT-TYPE
SYNTAX          Phase1GeneralEntry
MAX-ACCESS      not-accessible
STATUS          current
DESCRIPTION     "Entry in phase1General table."
INDEX        { phase1GeneralIndex }
::= { phase1GeneralTable 1 }

Phase1GeneralEntry ::= SEQUENCE {
phase1GeneralIndex	            Unsigned32,
phase1GeneralName	            DisplayString,
phase1GeneralVoltage	        Integer32,
phase1GeneralFrequency	        Integer32,
phase1GeneralConsumptionValue   Integer32,
phase1GeneralValueM15	        Integer32,
phase1GeneralTimestampM15	    Integer32,
phase1GeneralValueM30	        Integer32,
phase1GeneralTimestampM30	    Integer32,
phase1GeneralValueM60	        Integer32,
phase1GeneralTimestampM60	    Integer32,
phase1GeneralValueH24	        Integer32,
phase1GeneralTimestampH24	    Integer32}

phase1GeneralIndex OBJECT-TYPE
SYNTAX          Unsigned32
MAX-ACCESS      not-accessible
STATUS          current
DESCRIPTION     "Table Index."
::= { phase1GeneralEntry 1}

phase1GeneralName OBJECT-TYPE
SYNTAX          DisplayString
MAX-ACCESS      read-write
STATUS          current
DESCRIPTION     "Name of phase1."
::= { phase1GeneralEntry 2}

phase1GeneralVoltage OBJECT-TYPE
SYNTAX          Integer32
MAX-ACCESS      read-write
STATUS          current
DESCRIPTION     "Supply voltage level of the phase."
::= { phase1GeneralEntry 3}

phase1GeneralFrequency OBJECT-TYPE
SYNTAX          Integer32
MAX-ACCESS      read-write
STATUS          current
DESCRIPTION     "Supply frequency level of the phase."
::= { phase1GeneralEntry 4}

phase1GeneralConsumptionValue OBJECT-TYPE
SYNTAX          Integer32
MAX-ACCESS      read-write
STATUS          current
DESCRIPTION     "Consumption value of the phase."
::= { phase1GeneralEntry 5}

phase1GeneralValueM15 OBJECT-TYPE
SYNTAX          Integer32
MAX-ACCESS      read-write
STATUS          current
DESCRIPTION     "Last record of the consumtion Value in the last 15 minutes."
::= { phase1GeneralEntry 6}

phase1GeneralTimestampM15 OBJECT-TYPE
SYNTAX          Integer32
MAX-ACCESS      read-write
STATUS          current
DESCRIPTION     "Timestamp of the last consumtion Value record in the last 15 minutes."
::= { phase1GeneralEntry 7}

phase1GeneralValueM30 OBJECT-TYPE
SYNTAX          Integer32
MAX-ACCESS      read-write
STATUS          current
DESCRIPTION     "Last record of the consumtion Value in the last 30 minutes."
::= { phase1GeneralEntry 8}

phase1GeneralTimestampM30 OBJECT-TYPE
SYNTAX          Integer32
MAX-ACCESS      read-write
STATUS          current
DESCRIPTION     "Timestamp of the last consumtion Value record in the last 30 minutes."
::= { phase1GeneralEntry 9}

phase1GeneralValueM60 OBJECT-TYPE
SYNTAX          Integer32
MAX-ACCESS      read-write
STATUS          current
DESCRIPTION     "Last record of the consumtion Value in the last 60 minutes."
::= { phase1GeneralEntry 10}

phase1GeneralTimestampM60 OBJECT-TYPE
SYNTAX          Integer32
MAX-ACCESS      read-write
STATUS          current
DESCRIPTION     "Timestamp of the last consumtion Value record in the last 60 minutes."
::= { phase1GeneralEntry 11}

phase1GeneralValueH24 OBJECT-TYPE
SYNTAX          Integer32
MAX-ACCESS      read-write
STATUS          current
DESCRIPTION     "Last record of the consumtion Value in the last 24 hours."
::= { phase1GeneralEntry 12}

phase1GeneralTimestampH24 OBJECT-TYPE
SYNTAX          Integer32
MAX-ACCESS      read-write
STATUS          current
DESCRIPTION     "Timestamp of the last consumtion Value record in the last 24 hours."
::= { phase1GeneralEntry 13}

-------------------------------------------------------------------------------------------
-- Sensor PDU1 Voltage
-------------------------------------------------------------------------------------------

phase1VoltageTable OBJECT-TYPE
SYNTAX          SEQUENCE OF Phase1VoltageEntry
MAX-ACCESS      not-accessible
STATUS          current
DESCRIPTION     "Phase1Voltage values."
::= { phase1 2 }

phase1VoltageEntry OBJECT-TYPE
SYNTAX          Phase1VoltageEntry
MAX-ACCESS      not-accessible
STATUS          current
DESCRIPTION     "Entry in phase1Voltage table."
INDEX        { phase1VoltageIndex }
::= { phase1VoltageTable 1 }

Phase1VoltageEntry ::= SEQUENCE {
phase1VoltageIndex	    Unsigned32,
phase1VoltageValue	    Integer32,
phase1VoltageAlarm	    Unsigned32,
phase1VoltageMin	    Integer32,
phase1VoltageMax	    Integer32,
phase1VoltageTimestamp	Integer32}

phase1VoltageIndex OBJECT-TYPE
SYNTAX          Unsigned32
MAX-ACCESS      not-accessible
STATUS          current
DESCRIPTION     "Table Index."
::= { phase1VoltageEntry 1}

phase1VoltageValue OBJECT-TYPE
SYNTAX          Integer32
MAX-ACCESS      read-write
STATUS          current
DESCRIPTION     "Current value."
::= { phase1VoltageEntry 2}

phase1VoltageAlarm OBJECT-TYPE
SYNTAX          Unsigned32
MAX-ACCESS      read-write
STATUS          current
DESCRIPTION     "Current alarmstate."
::= { phase1VoltageEntry 3}

phase1VoltageMin OBJECT-TYPE
SYNTAX          Integer32
MAX-ACCESS      read-write
STATUS          current
DESCRIPTION     "Min. threshold of this value."
::= { phase1VoltageEntry 4}

phase1VoltageMax OBJECT-TYPE
SYNTAX          Integer32
MAX-ACCESS      read-write
STATUS          current
DESCRIPTION     "Max. threshold of this value."
::= { phase1VoltageEntry 5}

phase1VoltageTimestamp OBJECT-TYPE
SYNTAX          Integer32
MAX-ACCESS      read-write
STATUS          current
DESCRIPTION     "Timestamp of alarmstate change."
::= { phase1VoltageEntry 10}

-------------------------------------------------------------------------------------------
-- Sensor PDU1 Current
-------------------------------------------------------------------------------------------

phase1CurrentTable OBJECT-TYPE
SYNTAX          SEQUENCE OF Phase1CurrentEntry
MAX-ACCESS      not-accessible
STATUS          current
DESCRIPTION     "Phase1Current values."
::= { phase1 3 }

phase1CurrentEntry OBJECT-TYPE
SYNTAX          Phase1CurrentEntry
MAX-ACCESS      not-accessible
STATUS          current
DESCRIPTION     "Entry in phase1Current table."
INDEX        { phase1CurrentIndex }
::= { phase1CurrentTable 1 }

Phase1CurrentEntry ::= SEQUENCE {
phase1CurrentIndex	    Unsigned32,
phase1CurrentValue	    Integer32,
phase1CurrentAlarm	    Unsigned32,
phase1CurrentMax	    Integer32,
phase1CurrentTimestamp	Integer32}

phase1CurrentIndex OBJECT-TYPE
SYNTAX          Unsigned32
MAX-ACCESS      not-accessible
STATUS          current
DESCRIPTION     "Table Index."
::= { phase1CurrentEntry 1}

phase1CurrentValue OBJECT-TYPE
SYNTAX          Integer32
MAX-ACCESS      read-write
STATUS          current
DESCRIPTION     "Current value."
::= { phase1CurrentEntry 2}

phase1CurrentAlarm OBJECT-TYPE
SYNTAX          Unsigned32
MAX-ACCESS      read-write
STATUS          current
DESCRIPTION     "Current alarmstate."
::= { phase1CurrentEntry 3}

phase1CurrentMax OBJECT-TYPE
SYNTAX          Integer32
MAX-ACCESS      read-write
STATUS          current
DESCRIPTION     "Max. threshold of this value."
::= { phase1CurrentEntry 5}

phase1CurrentTimestamp OBJECT-TYPE
SYNTAX          Integer32
MAX-ACCESS      read-write
STATUS          current
DESCRIPTION     "Timestamp of alarmstate change."
::= { phase1CurrentEntry 10}

-------------------------------------------------------------------------------------------
-- Sensor PDU1 Activepower
-------------------------------------------------------------------------------------------

phase1ActivepowerTable OBJECT-TYPE
SYNTAX          SEQUENCE OF Phase1ActivepowerEntry
MAX-ACCESS      not-accessible
STATUS          current
DESCRIPTION     "Phase1Activepower values."
::= { phase1 4 }

phase1ActivepowerEntry OBJECT-TYPE
SYNTAX          Phase1ActivepowerEntry
MAX-ACCESS      not-accessible
STATUS          current
DESCRIPTION     "Entry in phase1Activepower table."
INDEX        { phase1ActivepowerIndex }
::= { phase1ActivepowerTable 1 }

Phase1ActivepowerEntry ::= SEQUENCE {
phase1ActivepowerIndex	    Unsigned32,
phase1ActivepowerValue	    Integer32,
phase1ActivepowerAlarm	    Unsigned32,
phase1ActivepowerMax	    Integer32,
phase1ActivepowerTimestamp	Integer32}

phase1ActivepowerIndex OBJECT-TYPE
SYNTAX          Unsigned32
MAX-ACCESS      not-accessible
STATUS          current
DESCRIPTION     "Table Index."
::= { phase1ActivepowerEntry 1}

phase1ActivepowerValue OBJECT-TYPE
SYNTAX          Integer32
MAX-ACCESS      read-write
STATUS          current
DESCRIPTION     "Activepower value."
::= { phase1ActivepowerEntry 2}

phase1ActivepowerAlarm OBJECT-TYPE
SYNTAX          Unsigned32
MAX-ACCESS      read-write
STATUS          current
DESCRIPTION     "Current alarmstate."
::= { phase1ActivepowerEntry 3}

phase1ActivepowerMax OBJECT-TYPE
SYNTAX          Integer32
MAX-ACCESS      read-write
STATUS          current
DESCRIPTION     "Max. threshold of this value."
::= { phase1ActivepowerEntry 5}

phase1ActivepowerTimestamp OBJECT-TYPE
SYNTAX          Integer32
MAX-ACCESS      read-write
STATUS          current
DESCRIPTION     "Timestamp of alarmstate change."
::= { phase1ActivepowerEntry 10}

-------------------------------------------------------------------------------------------
-- Sensor PDU1Reactivepower
-------------------------------------------------------------------------------------------

phase1ReactivepowerTable OBJECT-TYPE
SYNTAX          SEQUENCE OF Phase1ReactivepowerEntry
MAX-ACCESS      not-accessible
STATUS          current
DESCRIPTION     "Phase1Reactivepower values."
::= { phase1 5 }

phase1ReactivepowerEntry OBJECT-TYPE
SYNTAX          Phase1ReactivepowerEntry
MAX-ACCESS      not-accessible
STATUS          current
DESCRIPTION     "Entry in phase1Reactivepower table."
INDEX        { phase1ReactivepowerIndex }
::= { phase1ReactivepowerTable 1 }

Phase1ReactivepowerEntry ::= SEQUENCE {
phase1ReactivepowerIndex	    Unsigned32,
phase1ReactivepowerValue	    Integer32,
phase1ReactivepowerAlarm	    Unsigned32,
phase1ReactivepowerMax	        Integer32,
phase1ReactivepowerTimestamp	Integer32}

phase1ReactivepowerIndex OBJECT-TYPE
SYNTAX          Unsigned32
MAX-ACCESS      not-accessible
STATUS          current
DESCRIPTION     "Table Index."
::= { phase1ReactivepowerEntry 1}

phase1ReactivepowerValue OBJECT-TYPE
SYNTAX          Integer32
MAX-ACCESS      read-write
STATUS          current
DESCRIPTION     "Reactivepower value."
::= { phase1ReactivepowerEntry 2}

phase1ReactivepowerAlarm OBJECT-TYPE
SYNTAX          Unsigned32
MAX-ACCESS      read-write
STATUS          current
DESCRIPTION     "Current alarmstate."
::= { phase1ReactivepowerEntry 3}

phase1ReactivepowerMax OBJECT-TYPE
SYNTAX          Integer32
MAX-ACCESS      read-write
STATUS          current
DESCRIPTION     "Max. threshold of this value."
::= { phase1ReactivepowerEntry 5}

phase1ReactivepowerTimestamp OBJECT-TYPE
SYNTAX          Integer32
MAX-ACCESS      read-write
STATUS          current
DESCRIPTION     "Timestamp of alarmstate change."
::= { phase1ReactivepowerEntry 10}

-------------------------------------------------------------------------------------------
-- Sensor PDU1Apparentpower
-------------------------------------------------------------------------------------------

phase1ApparentpowerTable OBJECT-TYPE
SYNTAX          SEQUENCE OF Phase1ApparentpowerEntry
MAX-ACCESS      not-accessible
STATUS          current
DESCRIPTION     "Phase1Apparentpower values."
::= { phase1 6 }

phase1ApparentpowerEntry OBJECT-TYPE
SYNTAX          Phase1ApparentpowerEntry
MAX-ACCESS      not-accessible
STATUS          current
DESCRIPTION     "Entry in phase1Apparentpower table."
INDEX        { phase1ApparentpowerIndex }
::= { phase1ApparentpowerTable 1 }

Phase1ApparentpowerEntry ::= SEQUENCE {
phase1ApparentpowerIndex	    Unsigned32,
phase1ApparentpowerValue	    Integer32,
phase1ApparentpowerAlarm	    Unsigned32,
phase1ApparentpowerMax	        Integer32,
phase1ApparentpowerTimestamp	Integer32}

phase1ApparentpowerIndex OBJECT-TYPE
SYNTAX          Unsigned32
MAX-ACCESS      not-accessible
STATUS          current
DESCRIPTION     "Table Index."
::= { phase1ApparentpowerEntry 1}

phase1ApparentpowerValue OBJECT-TYPE
SYNTAX          Integer32
MAX-ACCESS      read-write
STATUS          current
DESCRIPTION     "Apparentpower value."
::= { phase1ApparentpowerEntry 2}

phase1ApparentpowerAlarm OBJECT-TYPE
SYNTAX          Unsigned32
MAX-ACCESS      read-write
STATUS          current
DESCRIPTION     "Current alarmstate."
::= { phase1ApparentpowerEntry 3}

phase1ApparentpowerMax OBJECT-TYPE
SYNTAX          Integer32
MAX-ACCESS      read-write
STATUS          current
DESCRIPTION     "Max. threshold of this value."
::= { phase1ApparentpowerEntry 5}

phase1ApparentpowerTimestamp OBJECT-TYPE
SYNTAX          Integer32
MAX-ACCESS      read-write
STATUS          current
DESCRIPTION     "Timestamp of alarmstate change."
::= { phase1ApparentpowerEntry 10}

-------------------------------------------------------------------------------------------
-- Sensor PDU1Frequency
-------------------------------------------------------------------------------------------

phase1FrequencyTable OBJECT-TYPE
SYNTAX          SEQUENCE OF Phase1FrequencyEntry
MAX-ACCESS      not-accessible
STATUS          current
DESCRIPTION     "Phase1Frequency values."
::= { phase1 7 }

phase1FrequencyEntry OBJECT-TYPE
SYNTAX          Phase1FrequencyEntry
MAX-ACCESS      not-accessible
STATUS          current
DESCRIPTION     "Entry in phase1Frequency table."
INDEX        { phase1FrequencyIndex }
::= { phase1FrequencyTable 1 }

Phase1FrequencyEntry ::= SEQUENCE {
phase1FrequencyIndex	    Unsigned32,
phase1FrequencyValue	    Integer32,
phase1FrequencyAlarm	    Unsigned32,
phase1FrequencyMax	        Integer32,
phase1FrequencyTimestamp	Integer32}

phase1FrequencyIndex OBJECT-TYPE
SYNTAX          Unsigned32
MAX-ACCESS      not-accessible
STATUS          current
DESCRIPTION     "Table Index."
::= { phase1FrequencyEntry 1}

phase1FrequencyValue OBJECT-TYPE
SYNTAX          Integer32
MAX-ACCESS      read-write
STATUS          current
DESCRIPTION     "Frequency value."
::= { phase1FrequencyEntry 2}

phase1FrequencyAlarm OBJECT-TYPE
SYNTAX          Unsigned32
MAX-ACCESS      read-write
STATUS          current
DESCRIPTION     "Current alarmstate."
::= { phase1FrequencyEntry 3}

phase1FrequencyMax OBJECT-TYPE
SYNTAX          Integer32
MAX-ACCESS      read-write
STATUS          current
DESCRIPTION     "Max. hysterese of this value."
::= { phase1FrequencyEntry 5}

phase1FrequencyTimestamp OBJECT-TYPE
SYNTAX          Integer32
MAX-ACCESS      read-write
STATUS          current
DESCRIPTION     "Timestamp of alarmstate change."
::= { phase1FrequencyEntry 10}

-------------------------------------------------------------------------------------------
-- Sensor phase2
-------------------------------------------------------------------------------------------

-------------------------------------------------------------------------------------------
-- phase2 General
-------------------------------------------------------------------------------------------

phase2GeneralTable OBJECT-TYPE
SYNTAX          SEQUENCE OF Phase2GeneralEntry
MAX-ACCESS      not-accessible
STATUS          current
DESCRIPTION     "Phase2General values."
::= { phase2 1 }

phase2GeneralEntry OBJECT-TYPE
SYNTAX          Phase2GeneralEntry
MAX-ACCESS      not-accessible
STATUS          current
DESCRIPTION     "Entry in phase2General table."
INDEX        { phase2GeneralIndex }
::= { phase2GeneralTable 1 }

Phase2GeneralEntry ::= SEQUENCE {
phase2GeneralIndex	            Unsigned32,
phase2GeneralName	            DisplayString,
phase2GeneralVoltage	        Integer32,
phase2GeneralFrequency	        Integer32,
phase2GeneralConsumptionValue	Integer32,
phase2GeneralValueM15	        Integer32,
phase2GeneralTimestampM15	    Integer32,
phase2GeneralValueM30	        Integer32,
phase2GeneralTimestampM30	    Integer32,
phase2GeneralValueM60	        Integer32,
phase2GeneralTimestampM60	    Integer32,
phase2GeneralValueH24	        Integer32,
phase2GeneralTimestampH24	    Integer32}

phase2GeneralIndex OBJECT-TYPE
SYNTAX          Unsigned32
MAX-ACCESS      not-accessible
STATUS          current
DESCRIPTION     "Table Index."
::= { phase2GeneralEntry 1}

phase2GeneralName OBJECT-TYPE
SYNTAX          DisplayString
MAX-ACCESS      read-write
STATUS          current
DESCRIPTION     "Name of phase2."
::= { phase2GeneralEntry 2}

phase2GeneralVoltage OBJECT-TYPE
SYNTAX          Integer32
MAX-ACCESS      read-write
STATUS          current
DESCRIPTION     "Supply voltage level of the phase."
::= { phase2GeneralEntry 3}

phase2GeneralFrequency OBJECT-TYPE
SYNTAX          Integer32
MAX-ACCESS      read-write
STATUS          current
DESCRIPTION     "Supply frequency level of the phase."
::= { phase2GeneralEntry 4}

phase2GeneralConsumptionValue OBJECT-TYPE
SYNTAX          Integer32
MAX-ACCESS      read-write
STATUS          current
DESCRIPTION     "Consumption value of the phase."
::= { phase2GeneralEntry 5}

phase2GeneralValueM15 OBJECT-TYPE
SYNTAX          Integer32
MAX-ACCESS      read-write
STATUS          current
DESCRIPTION     "Last record of the consumtion Value in the last 15 minutes."
::= { phase2GeneralEntry 6}

phase2GeneralTimestampM15 OBJECT-TYPE
SYNTAX          Integer32
MAX-ACCESS      read-write
STATUS          current
DESCRIPTION     "Timestamp of the last consumtion Value record in the last 15 minutes."
::= { phase2GeneralEntry 7}

phase2GeneralValueM30 OBJECT-TYPE
SYNTAX          Integer32
MAX-ACCESS      read-write
STATUS          current
DESCRIPTION     "Last record of the consumtion Value in the last 30 minutes."
::= { phase2GeneralEntry 8}

phase2GeneralTimestampM30 OBJECT-TYPE
SYNTAX          Integer32
MAX-ACCESS      read-write
STATUS          current
DESCRIPTION     "Timestamp of the last consumtion Value record in the last 30 minutes."
::= { phase2GeneralEntry 9}

phase2GeneralValueM60 OBJECT-TYPE
SYNTAX          Integer32
MAX-ACCESS      read-write
STATUS          current
DESCRIPTION     "Last record of the consumtion Value in the last 60 minutes."
::= { phase2GeneralEntry 10}

phase2GeneralTimestampM60 OBJECT-TYPE
SYNTAX          Integer32
MAX-ACCESS      read-write
STATUS          current
DESCRIPTION     "Timestamp of the last consumtion Value record in the last 60 minutes."
::= { phase2GeneralEntry 11}

phase2GeneralValueH24 OBJECT-TYPE
SYNTAX          Integer32
MAX-ACCESS      read-write
STATUS          current
DESCRIPTION     "Last record of the consumtion Value in the last 24 hours."
::= { phase2GeneralEntry 12}

phase2GeneralTimestampH24 OBJECT-TYPE
SYNTAX          Integer32
MAX-ACCESS      read-write
STATUS          current
DESCRIPTION     "Timestamp of the last consumtion Value record in the last 24 hours."
::= { phase2GeneralEntry 13}

-------------------------------------------------------------------------------------------
-- Sensor PDU2 Voltage
-------------------------------------------------------------------------------------------

phase2VoltageTable OBJECT-TYPE
SYNTAX          SEQUENCE OF Phase2VoltageEntry
MAX-ACCESS      not-accessible
STATUS          current
DESCRIPTION     "Phase1Voltage values."
::= { phase2 2 }

phase2VoltageEntry OBJECT-TYPE
SYNTAX          Phase2VoltageEntry
MAX-ACCESS      not-accessible
STATUS          current
DESCRIPTION     "Entry in phase2Voltage table."
INDEX        { phase2VoltageIndex }
::= { phase2VoltageTable 1 }

Phase2VoltageEntry ::= SEQUENCE {
phase2VoltageIndex	    Unsigned32,
phase2VoltageValue	    Integer32,
phase2VoltageAlarm	    Unsigned32,
phase2VoltageMin	    Integer32,
phase2VoltageMax	    Integer32,
phase2VoltageTimestamp	Integer32}

phase2VoltageIndex OBJECT-TYPE
SYNTAX          Unsigned32
MAX-ACCESS      not-accessible
STATUS          current
DESCRIPTION     "Table Index."
::= { phase2VoltageEntry 1}

phase2VoltageValue OBJECT-TYPE
SYNTAX          Integer32
MAX-ACCESS      read-write
STATUS          current
DESCRIPTION     "Current value."
::= { phase2VoltageEntry 2}

phase2VoltageAlarm OBJECT-TYPE
SYNTAX          Unsigned32
MAX-ACCESS      read-write
STATUS          current
DESCRIPTION     "Current alarmstate."
::= { phase2VoltageEntry 3}

phase2VoltageMin OBJECT-TYPE
SYNTAX          Integer32
MAX-ACCESS      read-write
STATUS          current
DESCRIPTION     "Min. threshold of this value."
::= { phase2VoltageEntry 4}

phase2VoltageMax OBJECT-TYPE
SYNTAX          Integer32
MAX-ACCESS      read-write
STATUS          current
DESCRIPTION     "Max. threshold of this value."
::= { phase2VoltageEntry 5}

phase2VoltageTimestamp OBJECT-TYPE
SYNTAX          Integer32
MAX-ACCESS      read-write
STATUS          current
DESCRIPTION     "Timestamp of alarmstate change."
::= { phase2VoltageEntry 10}

-------------------------------------------------------------------------------------------
-- Sensor PDU2 Current
-------------------------------------------------------------------------------------------

phase2CurrentTable OBJECT-TYPE
SYNTAX          SEQUENCE OF Phase2CurrentEntry
MAX-ACCESS      not-accessible
STATUS          current
DESCRIPTION     "Phase1Current values."
::= { phase2 3 }

phase2CurrentEntry OBJECT-TYPE
SYNTAX          Phase2CurrentEntry
MAX-ACCESS      not-accessible
STATUS          current
DESCRIPTION     "Entry in phase2Current table."
INDEX        { phase2CurrentIndex }
::= { phase2CurrentTable 1 }

Phase2CurrentEntry ::= SEQUENCE {
phase2CurrentIndex	    Unsigned32,
phase2CurrentValue	    Integer32,
phase2CurrentAlarm	    Unsigned32,
phase2CurrentMax	    Integer32,
phase2CurrentTimestamp	Integer32}

phase2CurrentIndex OBJECT-TYPE
SYNTAX          Unsigned32
MAX-ACCESS      not-accessible
STATUS          current
DESCRIPTION     "Table Index."
::= { phase2CurrentEntry 1}

phase2CurrentValue OBJECT-TYPE
SYNTAX          Integer32
MAX-ACCESS      read-write
STATUS          current
DESCRIPTION     "Current value."
::= { phase2CurrentEntry 2}

phase2CurrentAlarm OBJECT-TYPE
SYNTAX          Unsigned32
MAX-ACCESS      read-write
STATUS          current
DESCRIPTION     "Current alarmstate."
::= { phase2CurrentEntry 3}

phase2CurrentMax OBJECT-TYPE
SYNTAX          Integer32
MAX-ACCESS      read-write
STATUS          current
DESCRIPTION     "Max. threshold of this value."
::= { phase2CurrentEntry 5}

phase2CurrentTimestamp OBJECT-TYPE
SYNTAX          Integer32
MAX-ACCESS      read-write
STATUS          current
DESCRIPTION     "Timestamp of alarmstate change."
::= { phase2CurrentEntry 10}

-------------------------------------------------------------------------------------------
-- Sensor PDU2 Activepower
-------------------------------------------------------------------------------------------

phase2ActivepowerTable OBJECT-TYPE
SYNTAX          SEQUENCE OF Phase2ActivepowerEntry
MAX-ACCESS      not-accessible
STATUS          current
DESCRIPTION     "Phase2Activepower values."
::= { phase2 4 }

phase2ActivepowerEntry OBJECT-TYPE
SYNTAX          Phase2ActivepowerEntry
MAX-ACCESS      not-accessible
STATUS          current
DESCRIPTION     "Entry in phase2Activepower table."
INDEX        { phase2ActivepowerIndex }
::= { phase2ActivepowerTable 1 }

Phase2ActivepowerEntry ::= SEQUENCE {
phase2ActivepowerIndex	    Unsigned32,
phase2ActivepowerValue	    Integer32,
phase2ActivepowerAlarm	    Unsigned32,
phase2ActivepowerMax	    Integer32,
phase2ActivepowerTimestamp	Integer32}

phase2ActivepowerIndex OBJECT-TYPE
SYNTAX          Unsigned32
MAX-ACCESS      not-accessible
STATUS          current
DESCRIPTION     "Table Index."
::= { phase2ActivepowerEntry 1}

phase2ActivepowerValue OBJECT-TYPE
SYNTAX          Integer32
MAX-ACCESS      read-write
STATUS          current
DESCRIPTION     "Activepower value."
::= { phase2ActivepowerEntry 2}

phase2ActivepowerAlarm OBJECT-TYPE
SYNTAX          Unsigned32
MAX-ACCESS      read-write
STATUS          current
DESCRIPTION     "Current alarmstate."
::= { phase2ActivepowerEntry 3}

phase2ActivepowerMax OBJECT-TYPE
SYNTAX          Integer32
MAX-ACCESS      read-write
STATUS          current
DESCRIPTION     "Max. threshold of this value."
::= { phase2ActivepowerEntry 5}

phase2ActivepowerTimestamp OBJECT-TYPE
SYNTAX          Integer32
MAX-ACCESS      read-write
STATUS          current
DESCRIPTION     "Timestamp of alarmstate change."
::= { phase2ActivepowerEntry 10}

-------------------------------------------------------------------------------------------
-- Sensor PDU2Reactivepower
-------------------------------------------------------------------------------------------

phase2ReactivepowerTable OBJECT-TYPE
SYNTAX          SEQUENCE OF Phase2ReactivepowerEntry
MAX-ACCESS      not-accessible
STATUS          current
DESCRIPTION     "Phase1Reactivepower values."
::= { phase2 5 }

phase2ReactivepowerEntry OBJECT-TYPE
SYNTAX          Phase2ReactivepowerEntry
MAX-ACCESS      not-accessible
STATUS          current
DESCRIPTION     "Entry in phase2Reactivepower table."
INDEX        { phase2ReactivepowerIndex }
::= { phase2ReactivepowerTable 1 }

Phase2ReactivepowerEntry ::= SEQUENCE {
phase2ReactivepowerIndex	    Unsigned32,
phase2ReactivepowerValue	    Integer32,
phase2ReactivepowerAlarm	    Unsigned32,
phase2ReactivepowerMax	        Integer32,
phase2ReactivepowerTimestamp	Integer32}

phase2ReactivepowerIndex OBJECT-TYPE
SYNTAX          Unsigned32
MAX-ACCESS      not-accessible
STATUS          current
DESCRIPTION     "Table Index."
::= { phase2ReactivepowerEntry 1}

phase2ReactivepowerValue OBJECT-TYPE
SYNTAX          Integer32
MAX-ACCESS      read-write
STATUS          current
DESCRIPTION     "Reactivepower value."
::= { phase2ReactivepowerEntry 2}

phase2ReactivepowerAlarm OBJECT-TYPE
SYNTAX          Unsigned32
MAX-ACCESS      read-write
STATUS          current
DESCRIPTION     "Current alarmstate."
::= { phase2ReactivepowerEntry 3}

phase2ReactivepowerMax OBJECT-TYPE
SYNTAX          Integer32
MAX-ACCESS      read-write
STATUS          current
DESCRIPTION     "Max. threshold of this value."
::= { phase2ReactivepowerEntry 5}

phase2ReactivepowerTimestamp OBJECT-TYPE
SYNTAX          Integer32
MAX-ACCESS      read-write
STATUS          current
DESCRIPTION     "Timestamp of alarmstate change."
::= { phase2ReactivepowerEntry 10}

-------------------------------------------------------------------------------------------
-- Sensor PDU2Apparentpower
-------------------------------------------------------------------------------------------

phase2ApparentpowerTable OBJECT-TYPE
SYNTAX          SEQUENCE OF Phase2ApparentpowerEntry
MAX-ACCESS      not-accessible
STATUS          current
DESCRIPTION     "Phase2Apparentpower values."
::= { phase2 6 }

phase2ApparentpowerEntry OBJECT-TYPE
SYNTAX          Phase2ApparentpowerEntry
MAX-ACCESS      not-accessible
STATUS          current
DESCRIPTION     "Entry in phase2Apparentpower table."
INDEX        { phase2ApparentpowerIndex }
::= { phase2ApparentpowerTable 1 }

Phase2ApparentpowerEntry ::= SEQUENCE {
phase2ApparentpowerIndex	    Unsigned32,
phase2ApparentpowerValue	    Integer32,
phase2ApparentpowerAlarm	    Unsigned32,
phase2ApparentpowerMax	        Integer32,
phase2ApparentpowerTimestamp	Integer32}

phase2ApparentpowerIndex OBJECT-TYPE
SYNTAX          Unsigned32
MAX-ACCESS      not-accessible
STATUS          current
DESCRIPTION     "Table Index."
::= { phase2ApparentpowerEntry 1}

phase2ApparentpowerValue OBJECT-TYPE
SYNTAX          Integer32
MAX-ACCESS      read-write
STATUS          current
DESCRIPTION     "Apparentpower value."
::= { phase2ApparentpowerEntry 2}

phase2ApparentpowerAlarm OBJECT-TYPE
SYNTAX          Unsigned32
MAX-ACCESS      read-write
STATUS          current
DESCRIPTION     "Current alarmstate."
::= { phase2ApparentpowerEntry 3}

phase2ApparentpowerMax OBJECT-TYPE
SYNTAX          Integer32
MAX-ACCESS      read-write
STATUS          current
DESCRIPTION     "Max. threshold of this value."
::= { phase2ApparentpowerEntry 5}

phase2ApparentpowerTimestamp OBJECT-TYPE
SYNTAX          Integer32
MAX-ACCESS      read-write
STATUS          current
DESCRIPTION     "Timestamp of alarmstate change."
::= { phase2ApparentpowerEntry 10}

-------------------------------------------------------------------------------------------
-- Sensor PDU2Frequency
-------------------------------------------------------------------------------------------

phase2FrequencyTable OBJECT-TYPE
SYNTAX          SEQUENCE OF Phase2FrequencyEntry
MAX-ACCESS      not-accessible
STATUS          current
DESCRIPTION     "Phase1Frequency values."
::= { phase2 7 }

phase2FrequencyEntry OBJECT-TYPE
SYNTAX          Phase2FrequencyEntry
MAX-ACCESS      not-accessible
STATUS          current
DESCRIPTION     "Entry in phase2Frequency table."
INDEX        { phase2FrequencyIndex }
::= { phase2FrequencyTable 1 }

Phase2FrequencyEntry ::= SEQUENCE {
phase2FrequencyIndex	    Unsigned32,
phase2FrequencyValue	    Integer32,
phase2FrequencyAlarm	    Unsigned32,
phase2FrequencyMax	        Integer32,
phase2FrequencyTimestamp	Integer32}

phase2FrequencyIndex OBJECT-TYPE
SYNTAX          Unsigned32
MAX-ACCESS      not-accessible
STATUS          current
DESCRIPTION     "Table Index."
::= { phase2FrequencyEntry 1}

phase2FrequencyValue OBJECT-TYPE
SYNTAX          Integer32
MAX-ACCESS      read-write
STATUS          current
DESCRIPTION     "Frequency value."
::= { phase2FrequencyEntry 2}

phase2FrequencyAlarm OBJECT-TYPE
SYNTAX          Unsigned32
MAX-ACCESS      read-write
STATUS          current
DESCRIPTION     "Current alarmstate."
::= { phase2FrequencyEntry 3}

phase2FrequencyMax OBJECT-TYPE
SYNTAX          Integer32
MAX-ACCESS      read-write
STATUS          current
DESCRIPTION     "Max. hysterese of this value."
::= { phase2FrequencyEntry 5}

phase2FrequencyTimestamp OBJECT-TYPE
SYNTAX          Integer32
MAX-ACCESS      read-write
STATUS          current
DESCRIPTION     "Timestamp of alarmstate change."
::= { phase2FrequencyEntry 10}

-------------------------------------------------------------------------------------------
-- Sensor phase3
-------------------------------------------------------------------------------------------

-------------------------------------------------------------------------------------------
-- phase3 General
-------------------------------------------------------------------------------------------

phase3GeneralTable OBJECT-TYPE
SYNTAX          SEQUENCE OF Phase3GeneralEntry
MAX-ACCESS      not-accessible
STATUS          current
DESCRIPTION     "Phase1General values."
::= { phase3 1 }

phase3GeneralEntry OBJECT-TYPE
SYNTAX          Phase3GeneralEntry
MAX-ACCESS      not-accessible
STATUS          current
DESCRIPTION     "Entry in phase3General table."
INDEX        { phase3GeneralIndex }
::= { phase3GeneralTable 1 }

Phase3GeneralEntry ::= SEQUENCE {
phase3GeneralIndex	            Unsigned32,
phase3GeneralName	            DisplayString,
phase3GeneralVoltage	        Integer32,
phase3GeneralFrequency	        Integer32,
phase3GeneralConsumptionValue	Integer32,
phase3GeneralValueM15	        Integer32,
phase3GeneralTimestampM15	    Integer32,
phase3GeneralValueM30	        Integer32,
phase3GeneralTimestampM30	    Integer32,
phase3GeneralValueM60	        Integer32,
phase3GeneralTimestampM60	    Integer32,
phase3GeneralValueH24	        Integer32,
phase3GeneralTimestampH24	    Integer32}

phase3GeneralIndex OBJECT-TYPE
SYNTAX          Unsigned32
MAX-ACCESS      not-accessible
STATUS          current
DESCRIPTION     "Table Index."
::= { phase3GeneralEntry 1}

phase3GeneralName OBJECT-TYPE
SYNTAX          DisplayString
MAX-ACCESS      read-write
STATUS          current
DESCRIPTION     "Name of phase3."
::= { phase3GeneralEntry 2}

phase3GeneralVoltage OBJECT-TYPE
SYNTAX          Integer32
MAX-ACCESS      read-write
STATUS          current
DESCRIPTION     "Supply voltage level of the phase."
::= { phase3GeneralEntry 3}

phase3GeneralFrequency OBJECT-TYPE
SYNTAX          Integer32
MAX-ACCESS      read-write
STATUS          current
DESCRIPTION     "Supply frequency level of the phase."
::= { phase3GeneralEntry 4}

phase3GeneralConsumptionValue OBJECT-TYPE
SYNTAX          Integer32
MAX-ACCESS      read-write
STATUS          current
DESCRIPTION     "Consumption value of the phase."
::= { phase3GeneralEntry 5}

phase3GeneralValueM15 OBJECT-TYPE
SYNTAX          Integer32
MAX-ACCESS      read-write
STATUS          current
DESCRIPTION     "Last record of the consumtion Value in the last 15 minutes."
::= { phase3GeneralEntry 6}

phase3GeneralTimestampM15 OBJECT-TYPE
SYNTAX          Integer32
MAX-ACCESS      read-write
STATUS          current
DESCRIPTION     "Timestamp of the last consumtion Value record in the last 15 minutes."
::= { phase3GeneralEntry 7}

phase3GeneralValueM30 OBJECT-TYPE
SYNTAX          Integer32
MAX-ACCESS      read-write
STATUS          current
DESCRIPTION     "Last record of the consumtion Value in the last 30 minutes."
::= { phase3GeneralEntry 8}

phase3GeneralTimestampM30 OBJECT-TYPE
SYNTAX          Integer32
MAX-ACCESS      read-write
STATUS          current
DESCRIPTION     "Timestamp of the last consumtion Value record in the last 30 minutes."
::= { phase3GeneralEntry 9}

phase3GeneralValueM60 OBJECT-TYPE
SYNTAX          Integer32
MAX-ACCESS      read-write
STATUS          current
DESCRIPTION     "Last record of the consumtion Value in the last 60 minutes."
::= { phase3GeneralEntry 10}

phase3GeneralTimestampM60 OBJECT-TYPE
SYNTAX          Integer32
MAX-ACCESS      read-write
STATUS          current
DESCRIPTION     "Timestamp of the last consumtion Value record in the last 60 minutes."
::= { phase3GeneralEntry 11}

phase3GeneralValueH24 OBJECT-TYPE
SYNTAX          Integer32
MAX-ACCESS      read-write
STATUS          current
DESCRIPTION     "Last record of the consumtion Value in the last 24 hours."
::= { phase3GeneralEntry 12}

phase3GeneralTimestampH24 OBJECT-TYPE
SYNTAX          Integer32
MAX-ACCESS      read-write
STATUS          current
DESCRIPTION     "Timestamp of the last consumtion Value record in the last 24 hours."
::= { phase3GeneralEntry 13}

-------------------------------------------------------------------------------------------
-- Sensor PDU3 Voltage
-------------------------------------------------------------------------------------------

phase3VoltageTable OBJECT-TYPE
SYNTAX          SEQUENCE OF Phase3VoltageEntry
MAX-ACCESS      not-accessible
STATUS          current
DESCRIPTION     "Phase3Voltage values."
::= { phase3 2 }

phase3VoltageEntry OBJECT-TYPE
SYNTAX          Phase3VoltageEntry
MAX-ACCESS      not-accessible
STATUS          current
DESCRIPTION     "Entry in phase3Voltage table."
INDEX        { phase3VoltageIndex }
::= { phase3VoltageTable 1 }

Phase3VoltageEntry ::= SEQUENCE {
phase3VoltageIndex	    Unsigned32,
phase3VoltageValue	    Integer32,
phase3VoltageAlarm	    Unsigned32,
phase3VoltageMin	    Integer32,
phase3VoltageMax	    Integer32,
phase3VoltageTimestamp	Integer32}

phase3VoltageIndex OBJECT-TYPE
SYNTAX          Unsigned32
MAX-ACCESS      not-accessible
STATUS          current
DESCRIPTION     "Table Index."
::= { phase3VoltageEntry 1}

phase3VoltageValue OBJECT-TYPE
SYNTAX          Integer32
MAX-ACCESS      read-write
STATUS          current
DESCRIPTION     "Current value."
::= { phase3VoltageEntry 2}

phase3VoltageAlarm OBJECT-TYPE
SYNTAX          Unsigned32
MAX-ACCESS      read-write
STATUS          current
DESCRIPTION     "Current alarmstate."
::= { phase3VoltageEntry 3}

phase3VoltageMin OBJECT-TYPE
SYNTAX          Integer32
MAX-ACCESS      read-write
STATUS          current
DESCRIPTION     "Min. threshold of this value."
::= { phase3VoltageEntry 4}

phase3VoltageMax OBJECT-TYPE
SYNTAX          Integer32
MAX-ACCESS      read-write
STATUS          current
DESCRIPTION     "Max. threshold of this value."
::= { phase3VoltageEntry 5}

phase3VoltageTimestamp OBJECT-TYPE
SYNTAX          Integer32
MAX-ACCESS      read-write
STATUS          current
DESCRIPTION     "Timestamp of alarmstate change."
::= { phase3VoltageEntry 10}

-------------------------------------------------------------------------------------------
-- Sensor PDU3 Current
-------------------------------------------------------------------------------------------

phase3CurrentTable OBJECT-TYPE
SYNTAX          SEQUENCE OF Phase3CurrentEntry
MAX-ACCESS      not-accessible
STATUS          current
DESCRIPTION     "Phase3Current values."
::= { phase3 3 }

phase3CurrentEntry OBJECT-TYPE
SYNTAX          Phase3CurrentEntry
MAX-ACCESS      not-accessible
STATUS          current
DESCRIPTION     "Entry in phase3Current table."
INDEX        { phase3CurrentIndex }
::= { phase3CurrentTable 1 }

Phase3CurrentEntry ::= SEQUENCE {
phase3CurrentIndex	    Unsigned32,
phase3CurrentValue	    Integer32,
phase3CurrentAlarm	    Unsigned32,
phase3CurrentMax	    Integer32,
phase3CurrentTimestamp	Integer32}

phase3CurrentIndex OBJECT-TYPE
SYNTAX          Unsigned32
MAX-ACCESS      not-accessible
STATUS          current
DESCRIPTION     "Table Index."
::= { phase3CurrentEntry 1}

phase3CurrentValue OBJECT-TYPE
SYNTAX          Integer32
MAX-ACCESS      read-write
STATUS          current
DESCRIPTION     "Current value."
::= { phase3CurrentEntry 2}

phase3CurrentAlarm OBJECT-TYPE
SYNTAX          Unsigned32
MAX-ACCESS      read-write
STATUS          current
DESCRIPTION     "Current alarmstate."
::= { phase3CurrentEntry 3}

phase3CurrentMax OBJECT-TYPE
SYNTAX          Integer32
MAX-ACCESS      read-write
STATUS          current
DESCRIPTION     "Max. threshold of this value."
::= { phase3CurrentEntry 5}

phase3CurrentTimestamp OBJECT-TYPE
SYNTAX          Integer32
MAX-ACCESS      read-write
STATUS          current
DESCRIPTION     "Timestamp of alarmstate change."
::= { phase3CurrentEntry 10}

-------------------------------------------------------------------------------------------
-- Sensor PDU3 Activepower
-------------------------------------------------------------------------------------------

phase3ActivepowerTable OBJECT-TYPE
SYNTAX          SEQUENCE OF Phase3ActivepowerEntry
MAX-ACCESS      not-accessible
STATUS          current
DESCRIPTION     "Phase3Activepower values."
::= { phase3 4 }

phase3ActivepowerEntry OBJECT-TYPE
SYNTAX          Phase3ActivepowerEntry
MAX-ACCESS      not-accessible
STATUS          current
DESCRIPTION     "Entry in phase3Activepower table."
INDEX        { phase3ActivepowerIndex }
::= { phase3ActivepowerTable 1 }

Phase3ActivepowerEntry ::= SEQUENCE {
phase3ActivepowerIndex	    Unsigned32,
phase3ActivepowerValue	    Integer32,
phase3ActivepowerAlarm	    Unsigned32,
phase3ActivepowerMax	    Integer32,
phase3ActivepowerTimestamp	Integer32}

phase3ActivepowerIndex OBJECT-TYPE
SYNTAX          Unsigned32
MAX-ACCESS      not-accessible
STATUS          current
DESCRIPTION     "Table Index."
::= { phase3ActivepowerEntry 1}

phase3ActivepowerValue OBJECT-TYPE
SYNTAX          Integer32
MAX-ACCESS      read-write
STATUS          current
DESCRIPTION     "Activepower value."
::= { phase3ActivepowerEntry 2}

phase3ActivepowerAlarm OBJECT-TYPE
SYNTAX          Unsigned32
MAX-ACCESS      read-write
STATUS          current
DESCRIPTION     "Current alarmstate."
::= { phase3ActivepowerEntry 3}

phase3ActivepowerMax OBJECT-TYPE
SYNTAX          Integer32
MAX-ACCESS      read-write
STATUS          current
DESCRIPTION     "Max. threshold of this value."
::= { phase3ActivepowerEntry 5}

phase3ActivepowerTimestamp OBJECT-TYPE
SYNTAX          Integer32
MAX-ACCESS      read-write
STATUS          current
DESCRIPTION     "Timestamp of alarmstate change."
::= { phase3ActivepowerEntry 10}

-------------------------------------------------------------------------------------------
-- Sensor PDU3Reactivepower
-------------------------------------------------------------------------------------------

phase3ReactivepowerTable OBJECT-TYPE
SYNTAX          SEQUENCE OF Phase3ReactivepowerEntry
MAX-ACCESS      not-accessible
STATUS          current
DESCRIPTION     "Phase3Reactivepower values."
::= { phase3 5 }

phase3ReactivepowerEntry OBJECT-TYPE
SYNTAX          Phase3ReactivepowerEntry
MAX-ACCESS      not-accessible
STATUS          current
DESCRIPTION     "Entry in phase3Reactivepower table."
INDEX        { phase3ReactivepowerIndex }
::= { phase3ReactivepowerTable 1 }

Phase3ReactivepowerEntry ::= SEQUENCE {
phase3ReactivepowerIndex	    Unsigned32,
phase3ReactivepowerValue	    Integer32,
phase3ReactivepowerAlarm	    Unsigned32,
phase3ReactivepowerMax	        Integer32,
phase3ReactivepowerTimestamp	Integer32}

phase3ReactivepowerIndex OBJECT-TYPE
SYNTAX          Unsigned32
MAX-ACCESS      not-accessible
STATUS          current
DESCRIPTION     "Table Index."
::= { phase3ReactivepowerEntry 1}

phase3ReactivepowerValue OBJECT-TYPE
SYNTAX          Integer32
MAX-ACCESS      read-write
STATUS          current
DESCRIPTION     "Reactivepower value."
::= { phase3ReactivepowerEntry 2}

phase3ReactivepowerAlarm OBJECT-TYPE
SYNTAX          Unsigned32
MAX-ACCESS      read-write
STATUS          current
DESCRIPTION     "Current alarmstate."
::= { phase3ReactivepowerEntry 3}

phase3ReactivepowerMax OBJECT-TYPE
SYNTAX          Integer32
MAX-ACCESS      read-write
STATUS          current
DESCRIPTION     "Max. threshold of this value."
::= { phase3ReactivepowerEntry 5}

phase3ReactivepowerTimestamp OBJECT-TYPE
SYNTAX          Integer32
MAX-ACCESS      read-write
STATUS          current
DESCRIPTION     "Timestamp of alarmstate change."
::= { phase3ReactivepowerEntry 10}

-------------------------------------------------------------------------------------------
-- Sensor PDU3Apparentpower
-------------------------------------------------------------------------------------------

phase3ApparentpowerTable OBJECT-TYPE
SYNTAX          SEQUENCE OF Phase3ApparentpowerEntry
MAX-ACCESS      not-accessible
STATUS          current
DESCRIPTION     "Phase3Apparentpower values."
::= { phase3 6 }

phase3ApparentpowerEntry OBJECT-TYPE
SYNTAX          Phase3ApparentpowerEntry
MAX-ACCESS      not-accessible
STATUS          current
DESCRIPTION     "Entry in phase3Apparentpower table."
INDEX        { phase3ApparentpowerIndex }
::= { phase3ApparentpowerTable 1 }

Phase3ApparentpowerEntry ::= SEQUENCE {
phase3ApparentpowerIndex	    Unsigned32,
phase3ApparentpowerValue	    Integer32,
phase3ApparentpowerAlarm	    Unsigned32,
phase3ApparentpowerMax	        Integer32,
phase3ApparentpowerTimestamp	Integer32}

phase3ApparentpowerIndex OBJECT-TYPE
SYNTAX          Unsigned32
MAX-ACCESS      not-accessible
STATUS          current
DESCRIPTION     "Table Index."
::= { phase3ApparentpowerEntry 1}

phase3ApparentpowerValue OBJECT-TYPE
SYNTAX          Integer32
MAX-ACCESS      read-write
STATUS          current
DESCRIPTION     "Apparentpower value."
::= { phase3ApparentpowerEntry 2}

phase3ApparentpowerAlarm OBJECT-TYPE
SYNTAX          Unsigned32
MAX-ACCESS      read-write
STATUS          current
DESCRIPTION     "Current alarmstate."
::= { phase3ApparentpowerEntry 3}

phase3ApparentpowerMax OBJECT-TYPE
SYNTAX          Integer32
MAX-ACCESS      read-write
STATUS          current
DESCRIPTION     "Max. threshold of this value."
::= { phase3ApparentpowerEntry 5}

phase3ApparentpowerTimestamp OBJECT-TYPE
SYNTAX          Integer32
MAX-ACCESS      read-write
STATUS          current
DESCRIPTION     "Timestamp of alarmstate change."
::= { phase3ApparentpowerEntry 10}

-------------------------------------------------------------------------------------------
-- Sensor PDU3Frequency
-------------------------------------------------------------------------------------------

phase3FrequencyTable OBJECT-TYPE
SYNTAX          SEQUENCE OF Phase3FrequencyEntry
MAX-ACCESS      not-accessible
STATUS          current
DESCRIPTION     "Phase3Frequency values."
::= { phase3 7 }

phase3FrequencyEntry OBJECT-TYPE
SYNTAX          Phase3FrequencyEntry
MAX-ACCESS      not-accessible
STATUS          current
DESCRIPTION     "Entry in phase3Frequency table."
INDEX        { phase3FrequencyIndex }
::= { phase3FrequencyTable 1 }

Phase3FrequencyEntry ::= SEQUENCE {
phase3FrequencyIndex	    Unsigned32,
phase3FrequencyValue	    Integer32,
phase3FrequencyAlarm	    Unsigned32,
phase3FrequencyMax	        Integer32,
phase3FrequencyTimestamp	Integer32}

phase3FrequencyIndex OBJECT-TYPE
SYNTAX          Unsigned32
MAX-ACCESS      not-accessible
STATUS          current
DESCRIPTION     "Table Index."
::= { phase3FrequencyEntry 1}

phase3FrequencyValue OBJECT-TYPE
SYNTAX          Integer32
MAX-ACCESS      read-write
STATUS          current
DESCRIPTION     "Frequency value."
::= { phase3FrequencyEntry 2}

phase3FrequencyAlarm OBJECT-TYPE
SYNTAX          Unsigned32
MAX-ACCESS      read-write
STATUS          current
DESCRIPTION     "Current alarmstate."
::= { phase3FrequencyEntry 3}

phase3FrequencyMax OBJECT-TYPE
SYNTAX          Integer32
MAX-ACCESS      read-write
STATUS          current
DESCRIPTION     "Max. hysterese of this value."
::= { phase3FrequencyEntry 5}

phase3FrequencyTimestamp OBJECT-TYPE
SYNTAX          Integer32
MAX-ACCESS      read-write
STATUS          current
DESCRIPTION     "Timestamp of alarmstate change."
::= { phase3FrequencyEntry 10}

-------------------------------------------------------------------------------------------
-- Sensor analoginputs
-------------------------------------------------------------------------------------------

-------------------------------------------------------------------------------------------
-- AnalogInput 1.
-------------------------------------------------------------------------------------------

analogInput1Table OBJECT-TYPE
SYNTAX          SEQUENCE OF AnalogInput1Entry
MAX-ACCESS      not-accessible
STATUS          current
DESCRIPTION     "Analog input 1 values."
::= { analoginputs 1 }

analogInput1Entry OBJECT-TYPE
SYNTAX          AnalogInput1Entry
MAX-ACCESS      not-accessible
STATUS          current
DESCRIPTION     "Entry in analog input 1 table."
INDEX        { analogInput1Index }
::= { analogInput1Table 1 }

AnalogInput1Entry ::= SEQUENCE {
analogInput1Index		Unsigned32,
analogInput1Name		DisplayString,
analogInput1Group		DisplayString,
analogInput1Value		Integer32,
analogInput1Alarm		Unsigned32,
analogInput1Min			Integer32,
analogInput1Max			Integer32,
analogInput1Multiplier	Unsigned32,
analogInput1Unit		DisplayString,
analogInput1Timestamp	Integer32}

analogInput1Index OBJECT-TYPE
SYNTAX          Unsigned32
MAX-ACCESS      not-accessible
STATUS          current
DESCRIPTION     "Table Index."
::= { analogInput1Entry 1}

analogInput1Name OBJECT-TYPE
SYNTAX          DisplayString
MAX-ACCESS      read-write
STATUS          current
DESCRIPTION     "Name of the analog input."
::= { analogInput1Entry 2}

analogInput1Group OBJECT-TYPE
SYNTAX          DisplayString
MAX-ACCESS      read-write
STATUS          current
DESCRIPTION     "Alarmgroup of the analog input."
::= { analogInput1Entry 3}

analogInput1Value OBJECT-TYPE
SYNTAX          Integer32
MAX-ACCESS      read-write
STATUS          current
DESCRIPTION     "Current value of the analog input."
::= { analogInput1Entry 4}

analogInput1Alarm OBJECT-TYPE
SYNTAX          Unsigned32
MAX-ACCESS      read-write
STATUS          current
DESCRIPTION     "Current alarmstate of the analog input."
::= { analogInput1Entry 5}

analogInput1Min OBJECT-TYPE
SYNTAX          Integer32
MAX-ACCESS      read-write
STATUS          current
DESCRIPTION     "Min. threshold of this value."
::= { analogInput1Entry 6}

analogInput1Max OBJECT-TYPE
SYNTAX          Integer32
MAX-ACCESS      read-write
STATUS          current
DESCRIPTION     "Max. threshold of this value."
::= { analogInput1Entry 7}

analogInput1Multiplier OBJECT-TYPE
SYNTAX          Unsigned32
MAX-ACCESS      read-write
STATUS          current
DESCRIPTION     "Multiplier of this value."
::= { analogInput1Entry 8}

analogInput1Unit OBJECT-TYPE
SYNTAX          DisplayString
MAX-ACCESS      read-write
STATUS          current
DESCRIPTION     "Unit of this value."
::= { analogInput1Entry 9}

analogInput1Timestamp OBJECT-TYPE
SYNTAX          Integer32
MAX-ACCESS      read-write
STATUS          current
DESCRIPTION     "Timestamp of alarmstate change."
::= { analogInput1Entry 10}

-------------------------------------------------------------------------------------------
-- AnalogInput 2.
-------------------------------------------------------------------------------------------

analogInput2Table OBJECT-TYPE
SYNTAX          SEQUENCE OF AnalogInput2Entry
MAX-ACCESS      not-accessible
STATUS          current
DESCRIPTION     "Analog input 2 values."
::= { analoginputs 2 }

analogInput2Entry OBJECT-TYPE
SYNTAX          AnalogInput2Entry
MAX-ACCESS      not-accessible
STATUS          current
DESCRIPTION     "Entry in analog input 2 table."
INDEX        { analogInput2Index }
::= { analogInput2Table 1 }

AnalogInput2Entry ::= SEQUENCE {
analogInput2Index		Unsigned32,
analogInput2Name		DisplayString,
analogInput2Group		DisplayString,
analogInput2Value		Integer32,
analogInput2Alarm		Unsigned32,
analogInput2Min			Integer32,
analogInput2Max			Integer32,
analogInput2Multiplier	Unsigned32,
analogInput2Unit		DisplayString,
analogInput2Timestamp	Integer32}

analogInput2Index OBJECT-TYPE
SYNTAX          Unsigned32
MAX-ACCESS      not-accessible
STATUS          current
DESCRIPTION     "Table Index."
::= { analogInput2Entry 1}

analogInput2Name OBJECT-TYPE
SYNTAX          DisplayString
MAX-ACCESS      read-write
STATUS          current
DESCRIPTION     "Name of the analog input."
::= { analogInput2Entry 2}

analogInput2Group OBJECT-TYPE
SYNTAX          DisplayString
MAX-ACCESS      read-write
STATUS          current
DESCRIPTION     "Alarmgroup of the analog input."
::= { analogInput2Entry 3}

analogInput2Value OBJECT-TYPE
SYNTAX          Integer32
MAX-ACCESS      read-write
STATUS          current
DESCRIPTION     "Current value of the analog input."
::= { analogInput2Entry 4}

analogInput2Alarm OBJECT-TYPE
SYNTAX          Unsigned32
MAX-ACCESS      read-write
STATUS          current
DESCRIPTION     "Current alarmstate of the analog input."
::= { analogInput2Entry 5}

analogInput2Min OBJECT-TYPE
SYNTAX          Integer32
MAX-ACCESS      read-write
STATUS          current
DESCRIPTION     "Min. threshold of this value."
::= { analogInput2Entry 6}

analogInput2Max OBJECT-TYPE
SYNTAX          Integer32
MAX-ACCESS      read-write
STATUS          current
DESCRIPTION     "Max. threshold of this value."
::= { analogInput2Entry 7}

analogInput2Multiplier OBJECT-TYPE
SYNTAX          Unsigned32
MAX-ACCESS      read-write
STATUS          current
DESCRIPTION     "Multiplier of this value."
::= { analogInput2Entry 8}

analogInput2Unit OBJECT-TYPE
SYNTAX          DisplayString
MAX-ACCESS      read-write
STATUS          current
DESCRIPTION     "Unit of this value."
::= { analogInput2Entry 9}

analogInput2Timestamp OBJECT-TYPE
SYNTAX          Integer32
MAX-ACCESS      read-write
STATUS          current
DESCRIPTION     "Timestamp of alarmstate change."
::= { analogInput2Entry 10}

-------------------------------------------------------------------------------------------
-- AnalogInput 3.
-------------------------------------------------------------------------------------------

analogInput3Table OBJECT-TYPE
SYNTAX          SEQUENCE OF AnalogInput3Entry
MAX-ACCESS      not-accessible
STATUS          current
DESCRIPTION     "Analog input 3 values."
::= { analoginputs 3 }

analogInput3Entry OBJECT-TYPE
SYNTAX          AnalogInput3Entry
MAX-ACCESS      not-accessible
STATUS          current
DESCRIPTION     "Entry in analog input 3 table."
INDEX        { analogInput3Index }
::= { analogInput3Table 1 }

AnalogInput3Entry ::= SEQUENCE {
analogInput3Index		Unsigned32,
analogInput3Name		DisplayString,
analogInput3Group		DisplayString,
analogInput3Value		Integer32,
analogInput3Alarm		Unsigned32,
analogInput3Min			Integer32,
analogInput3Max			Integer32,
analogInput3Multiplier	Unsigned32,
analogInput3Unit		DisplayString,
analogInput3Timestamp	Integer32}

analogInput3Index OBJECT-TYPE
SYNTAX          Unsigned32
MAX-ACCESS      not-accessible
STATUS          current
DESCRIPTION     "Table Index."
::= { analogInput3Entry 1}

analogInput3Name OBJECT-TYPE
SYNTAX          DisplayString
MAX-ACCESS      read-write
STATUS          current
DESCRIPTION     "Name of the analog input."
::= { analogInput3Entry 2}

analogInput3Group OBJECT-TYPE
SYNTAX          DisplayString
MAX-ACCESS      read-write
STATUS          current
DESCRIPTION     "Alarmgroup of the analog input."
::= { analogInput3Entry 3}

analogInput3Value OBJECT-TYPE
SYNTAX          Integer32
MAX-ACCESS      read-write
STATUS          current
DESCRIPTION     "Current value of the analog input."
::= { analogInput3Entry 4}

analogInput3Alarm OBJECT-TYPE
SYNTAX          Unsigned32
MAX-ACCESS      read-write
STATUS          current
DESCRIPTION     "Current alarmstate of the analog input."
::= { analogInput3Entry 5}

analogInput3Min OBJECT-TYPE
SYNTAX          Integer32
MAX-ACCESS      read-write
STATUS          current
DESCRIPTION     "Min. threshold of this value."
::= { analogInput3Entry 6}

analogInput3Max OBJECT-TYPE
SYNTAX          Integer32
MAX-ACCESS      read-write
STATUS          current
DESCRIPTION     "Max. threshold of this value.."
::= { analogInput3Entry 7}

analogInput3Multiplier OBJECT-TYPE
SYNTAX          Unsigned32
MAX-ACCESS      read-write
STATUS          current
DESCRIPTION     "Multiplier of this value."
::= { analogInput3Entry 8}

analogInput3Unit OBJECT-TYPE
SYNTAX          DisplayString
MAX-ACCESS      read-write
STATUS          current
DESCRIPTION     "Unit of this value."
::= { analogInput3Entry 9}

analogInput3Timestamp OBJECT-TYPE
SYNTAX          Integer32
MAX-ACCESS      read-write
STATUS          current
DESCRIPTION     "Timestamp of alarmstate change."
::= { analogInput3Entry 10}

-------------------------------------------------------------------------------------------
-- AnalogInput 4.
-------------------------------------------------------------------------------------------

analogInput4Table OBJECT-TYPE
SYNTAX          SEQUENCE OF AnalogInput4Entry
MAX-ACCESS      not-accessible
STATUS          current
DESCRIPTION     "Analog input 4 values."
::= { analoginputs 4 }

analogInput4Entry OBJECT-TYPE
SYNTAX          AnalogInput4Entry
MAX-ACCESS      not-accessible
STATUS          current
DESCRIPTION     "Entry in analog input 4 table."
INDEX        { analogInput4Index }
::= { analogInput4Table 1 }

AnalogInput4Entry ::= SEQUENCE {
analogInput4Index		Unsigned32,
analogInput4Name		DisplayString,
analogInput4Group		DisplayString,
analogInput4Value		Integer32,
analogInput4Alarm		Unsigned32,
analogInput4Min			Integer32,
analogInput4Max			Integer32,
analogInput4Multiplier	Unsigned32,
analogInput4Unit		DisplayString,
analogInput4Timestamp	Integer32}

analogInput4Index OBJECT-TYPE
SYNTAX          Unsigned32
MAX-ACCESS      not-accessible
STATUS          current
DESCRIPTION     "Table Index."
::= { analogInput4Entry 1}

analogInput4Name OBJECT-TYPE
SYNTAX          DisplayString
MAX-ACCESS      read-write
STATUS          current
DESCRIPTION     "Name of the analog input."
::= { analogInput4Entry 2}

analogInput4Group OBJECT-TYPE
SYNTAX          DisplayString
MAX-ACCESS      read-write
STATUS          current
DESCRIPTION     "Alarmgroup of the analog input."
::= { analogInput4Entry 3}

analogInput4Value OBJECT-TYPE
SYNTAX          Integer32
MAX-ACCESS      read-write
STATUS          current
DESCRIPTION     "Current value of the analog input."
::= { analogInput4Entry 4}

analogInput4Alarm OBJECT-TYPE
SYNTAX          Unsigned32
MAX-ACCESS      read-write
STATUS          current
DESCRIPTION     "Current alarmstate of the analog input."
::= { analogInput4Entry 5}

analogInput4Min OBJECT-TYPE
SYNTAX          Integer32
MAX-ACCESS      read-write
STATUS          current
DESCRIPTION     "Min. threshold of this value."
::= { analogInput4Entry 6}

analogInput4Max OBJECT-TYPE
SYNTAX          Integer32
MAX-ACCESS      read-write
STATUS          current
DESCRIPTION     "Max. threshold of this value.."
::= { analogInput4Entry 7}

analogInput4Multiplier OBJECT-TYPE
SYNTAX          Unsigned32
MAX-ACCESS      read-write
STATUS          current
DESCRIPTION     "Multiplier of this value."
::= { analogInput4Entry 8}

analogInput4Unit OBJECT-TYPE
SYNTAX          DisplayString
MAX-ACCESS      read-write
STATUS          current
DESCRIPTION     "Unit of this value."
::= { analogInput4Entry 9}

analogInput4Timestamp OBJECT-TYPE
SYNTAX          Integer32
MAX-ACCESS      read-write
STATUS          current
DESCRIPTION     "Timestamp of alarmstate change."
::= { analogInput4Entry 10}

-------------------------------------------------------------------------------------------
-- AnalogInput 5.
-------------------------------------------------------------------------------------------

analogInput5Table OBJECT-TYPE
SYNTAX          SEQUENCE OF AnalogInput5Entry
MAX-ACCESS      not-accessible
STATUS          current
DESCRIPTION     "Analog input 5 values."
::= { analoginputs 5 }

analogInput5Entry OBJECT-TYPE
SYNTAX          AnalogInput5Entry
MAX-ACCESS      not-accessible
STATUS          current
DESCRIPTION     "Entry in analog input 5 table."
INDEX        { analogInput5Index }
::= { analogInput5Table 1 }

AnalogInput5Entry ::= SEQUENCE {
analogInput5Index		Unsigned32,
analogInput5Name		DisplayString,
analogInput5Group		DisplayString,
analogInput5Value		Integer32,
analogInput5Alarm		Unsigned32,
analogInput5Min			Integer32,
analogInput5Max			Integer32,
analogInput5Multiplier	Unsigned32,
analogInput5Unit		DisplayString,
analogInput5Timestamp	Integer32}

analogInput5Index OBJECT-TYPE
SYNTAX          Unsigned32
MAX-ACCESS      not-accessible
STATUS          current
DESCRIPTION     "Table Index."
::= { analogInput5Entry 1}

analogInput5Name OBJECT-TYPE
SYNTAX          DisplayString
MAX-ACCESS      read-write
STATUS          current
DESCRIPTION     "Name of the analog input."
::= { analogInput5Entry 2}

analogInput5Group OBJECT-TYPE
SYNTAX          DisplayString
MAX-ACCESS      read-write
STATUS          current
DESCRIPTION     "Alarmgroup of the analog input."
::= { analogInput5Entry 3}

analogInput5Value OBJECT-TYPE
SYNTAX          Integer32
MAX-ACCESS      read-write
STATUS          current
DESCRIPTION     "Current value of the analog input."
::= { analogInput5Entry 4}

analogInput5Alarm OBJECT-TYPE
SYNTAX          Unsigned32
MAX-ACCESS      read-write
STATUS          current
DESCRIPTION     "Current alarmstate of the analog input."
::= { analogInput5Entry 5}

analogInput5Min OBJECT-TYPE
SYNTAX          Integer32
MAX-ACCESS      read-write
STATUS          current
DESCRIPTION     "Min. threshold of this value."
::= { analogInput5Entry 6}

analogInput5Max OBJECT-TYPE
SYNTAX          Integer32
MAX-ACCESS      read-write
STATUS          current
DESCRIPTION     "Max. threshold of this value.."
::= { analogInput5Entry 7}

analogInput5Multiplier OBJECT-TYPE
SYNTAX          Unsigned32
MAX-ACCESS      read-write
STATUS          current
DESCRIPTION     "Multiplier of this value."
::= { analogInput5Entry 8}

analogInput5Unit OBJECT-TYPE
SYNTAX          DisplayString
MAX-ACCESS      read-write
STATUS          current
DESCRIPTION     "Unit of this value."
::= { analogInput5Entry 9}

analogInput5Timestamp OBJECT-TYPE
SYNTAX          Integer32
MAX-ACCESS      read-write
STATUS          current
DESCRIPTION     "Timestamp of alarmstate change."
::= { analogInput5Entry 10}

-------------------------------------------------------------------------------------------
-- AnalogInput 6.
-------------------------------------------------------------------------------------------

analogInput6Table OBJECT-TYPE
SYNTAX          SEQUENCE OF AnalogInput6Entry
MAX-ACCESS      not-accessible
STATUS          current
DESCRIPTION     "Analog input 6 values."
::= { analoginputs 6 }

analogInput6Entry OBJECT-TYPE
SYNTAX          AnalogInput6Entry
MAX-ACCESS      not-accessible
STATUS          current
DESCRIPTION     "Entry in analog input 6 table."
INDEX        { analogInput6Index }
::= { analogInput6Table 1 }

AnalogInput6Entry ::= SEQUENCE {
analogInput6Index		Unsigned32,
analogInput6Name		DisplayString,
analogInput6Group		DisplayString,
analogInput6Value		Integer32,
analogInput6Alarm		Unsigned32,
analogInput6Min			Integer32,
analogInput6Max			Integer32,
analogInput6Multiplier	Unsigned32,
analogInput6Unit		DisplayString,
analogInput6Timestamp	Integer32}

analogInput6Index OBJECT-TYPE
SYNTAX          Unsigned32
MAX-ACCESS      not-accessible
STATUS          current
DESCRIPTION     "Table Index."
::= { analogInput6Entry 1}

analogInput6Name OBJECT-TYPE
SYNTAX          DisplayString
MAX-ACCESS      read-write
STATUS          current
DESCRIPTION     "Name of the analog input."
::= { analogInput6Entry 2}

analogInput6Group OBJECT-TYPE
SYNTAX          DisplayString
MAX-ACCESS      read-write
STATUS          current
DESCRIPTION     "Alarmgroup of the analog input."
::= { analogInput6Entry 3}

analogInput6Value OBJECT-TYPE
SYNTAX          Integer32
MAX-ACCESS      read-write
STATUS          current
DESCRIPTION     "Current value of the analog input."
::= { analogInput6Entry 4}

analogInput6Alarm OBJECT-TYPE
SYNTAX          Unsigned32
MAX-ACCESS      read-write
STATUS          current
DESCRIPTION     "Current alarmstate of the analog input."
::= { analogInput6Entry 5}

analogInput6Min OBJECT-TYPE
SYNTAX          Integer32
MAX-ACCESS      read-write
STATUS          current
DESCRIPTION     "Min. threshold of this value."
::= { analogInput6Entry 6}

analogInput6Max OBJECT-TYPE
SYNTAX          Integer32
MAX-ACCESS      read-write
STATUS          current
DESCRIPTION     "Max. threshold of this value.."
::= { analogInput6Entry 7}

analogInput6Multiplier OBJECT-TYPE
SYNTAX          Unsigned32
MAX-ACCESS      read-write
STATUS          current
DESCRIPTION     "Multiplier of this value."
::= { analogInput6Entry 8}

analogInput6Unit OBJECT-TYPE
SYNTAX          DisplayString
MAX-ACCESS      read-write
STATUS          current
DESCRIPTION     "Unit of this value."
::= { analogInput6Entry 9}

analogInput6Timestamp OBJECT-TYPE
SYNTAX          Integer32
MAX-ACCESS      read-write
STATUS          current
DESCRIPTION     "Timestamp of alarmstate change."
::= { analogInput6Entry 10}

-------------------------------------------------------------------------------------------
-- AnalogInput 7.
-------------------------------------------------------------------------------------------

analogInput7Table OBJECT-TYPE
SYNTAX          SEQUENCE OF AnalogInput7Entry
MAX-ACCESS      not-accessible
STATUS          current
DESCRIPTION     "Analog input 7 values."
::= { analoginputs 7 }

analogInput7Entry OBJECT-TYPE
SYNTAX          AnalogInput7Entry
MAX-ACCESS      not-accessible
STATUS          current
DESCRIPTION     "Entry in analog input 7 table."
INDEX        { analogInput7Index }
::= { analogInput7Table 1 }

AnalogInput7Entry ::= SEQUENCE {
analogInput7Index		Unsigned32,
analogInput7Name		DisplayString,
analogInput7Group		DisplayString,
analogInput7Value		Integer32,
analogInput7Alarm		Unsigned32,
analogInput7Min			Integer32,
analogInput7Max			Integer32,
analogInput7Multiplier	Unsigned32,
analogInput7Unit		DisplayString,
analogInput7Timestamp	Integer32}

analogInput7Index OBJECT-TYPE
SYNTAX          Unsigned32
MAX-ACCESS      not-accessible
STATUS          current
DESCRIPTION     "Table Index."
::= { analogInput7Entry 1}

analogInput7Name OBJECT-TYPE
SYNTAX          DisplayString
MAX-ACCESS      read-write
STATUS          current
DESCRIPTION     "Name of the analog input."
::= { analogInput7Entry 2}

analogInput7Group OBJECT-TYPE
SYNTAX          DisplayString
MAX-ACCESS      read-write
STATUS          current
DESCRIPTION     "Alarmgroup of the analog input."
::= { analogInput7Entry 3}

analogInput7Value OBJECT-TYPE
SYNTAX          Integer32
MAX-ACCESS      read-write
STATUS          current
DESCRIPTION     "Current value of the analog input."
::= { analogInput7Entry 4}

analogInput7Alarm OBJECT-TYPE
SYNTAX          Unsigned32
MAX-ACCESS      read-write
STATUS          current
DESCRIPTION     "Current alarmstate of the analog input."
::= { analogInput7Entry 5}

analogInput7Min OBJECT-TYPE
SYNTAX          Integer32
MAX-ACCESS      read-write
STATUS          current
DESCRIPTION     "Min. threshold of this value."
::= { analogInput7Entry 6}

analogInput7Max OBJECT-TYPE
SYNTAX          Integer32
MAX-ACCESS      read-write
STATUS          current
DESCRIPTION     "Max. threshold of this value.."
::= { analogInput7Entry 7}

analogInput7Multiplier OBJECT-TYPE
SYNTAX          Unsigned32
MAX-ACCESS      read-write
STATUS          current
DESCRIPTION     "Multiplier of this value."
::= { analogInput7Entry 8}

analogInput7Unit OBJECT-TYPE
SYNTAX          DisplayString
MAX-ACCESS      read-write
STATUS          current
DESCRIPTION     "Unit of this value."
::= { analogInput7Entry 9}

analogInput7Timestamp OBJECT-TYPE
SYNTAX          Integer32
MAX-ACCESS      read-write
STATUS          current
DESCRIPTION     "Timestamp of alarmstate change."
::= { analogInput7Entry 10}

-------------------------------------------------------------------------------------------
-- AnalogInput 8.
-------------------------------------------------------------------------------------------

analogInput8Table OBJECT-TYPE
SYNTAX          SEQUENCE OF AnalogInput8Entry
MAX-ACCESS      not-accessible
STATUS          current
DESCRIPTION     "Analog input 8 values."
::= { analoginputs 8 }

analogInput8Entry OBJECT-TYPE
SYNTAX          AnalogInput8Entry
MAX-ACCESS      not-accessible
STATUS          current
DESCRIPTION     "Entry in analog input 8 table."
INDEX        { analogInput8Index }
::= { analogInput8Table 1 }

AnalogInput8Entry ::= SEQUENCE {
analogInput8Index		Unsigned32,
analogInput8Name		DisplayString,
analogInput8Group		DisplayString,
analogInput8Value		Integer32,
analogInput8Alarm		Unsigned32,
analogInput8Min			Integer32,
analogInput8Max			Integer32,
analogInput8Multiplier	Unsigned32,
analogInput8Unit		DisplayString,
analogInput8Timestamp	Integer32}

analogInput8Index OBJECT-TYPE
SYNTAX          Unsigned32
MAX-ACCESS      not-accessible
STATUS          current
DESCRIPTION     "Table Index."
::= { analogInput8Entry 1}

analogInput8Name OBJECT-TYPE
SYNTAX          DisplayString
MAX-ACCESS      read-write
STATUS          current
DESCRIPTION     "Name of the analog input."
::= { analogInput8Entry 2}

analogInput8Group OBJECT-TYPE
SYNTAX          DisplayString
MAX-ACCESS      read-write
STATUS          current
DESCRIPTION     "Alarmgroup of the analog input."
::= { analogInput8Entry 3}

analogInput8Value OBJECT-TYPE
SYNTAX          Integer32
MAX-ACCESS      read-write
STATUS          current
DESCRIPTION     "Current value of the analog input."
::= { analogInput8Entry 4}

analogInput8Alarm OBJECT-TYPE
SYNTAX          Unsigned32
MAX-ACCESS      read-write
STATUS          current
DESCRIPTION     "Current alarmstate of the analog input."
::= { analogInput8Entry 5}

analogInput8Min OBJECT-TYPE
SYNTAX          Integer32
MAX-ACCESS      read-write
STATUS          current
DESCRIPTION     "Min. threshold of this value."
::= { analogInput8Entry 6}

analogInput8Max OBJECT-TYPE
SYNTAX          Integer32
MAX-ACCESS      read-write
STATUS          current
DESCRIPTION     "Max. threshold of this value.."
::= { analogInput8Entry 7}

analogInput8Multiplier OBJECT-TYPE
SYNTAX          Unsigned32
MAX-ACCESS      read-write
STATUS          current
DESCRIPTION     "Multiplier of this value."
::= { analogInput8Entry 8}

analogInput8Unit OBJECT-TYPE
SYNTAX          DisplayString
MAX-ACCESS      read-write
STATUS          current
DESCRIPTION     "Unit of this value."
::= { analogInput8Entry 9}

analogInput8Timestamp OBJECT-TYPE
SYNTAX          Integer32
MAX-ACCESS      read-write
STATUS          current
DESCRIPTION     "Timestamp of alarmstate change."
::= { analogInput8Entry 10}

-------------------------------------------------------------------------------------------
-- Sensor leakages
-------------------------------------------------------------------------------------------

-------------------------------------------------------------------------------------------
-- Leakage 1.
-------------------------------------------------------------------------------------------

leakage1Table OBJECT-TYPE
SYNTAX          SEQUENCE OF Leakage1Entry
MAX-ACCESS      not-accessible
STATUS          current
DESCRIPTION     "Leakage 1 values."
::= { leakages 1 }

leakage1Entry OBJECT-TYPE
SYNTAX          Leakage1Entry
MAX-ACCESS      not-accessible
STATUS          current
DESCRIPTION     "Entry in leakage 1 table."
INDEX        { leakage1Index }
::= { leakage1Table 1 }

Leakage1Entry ::= SEQUENCE {
leakage1Index		Unsigned32,
leakage1Name		DisplayString,
leakage1Value		Unsigned32,
leakage1Alarm		Unsigned32,
leakage1Timestamp	Integer32}

leakage1Index OBJECT-TYPE
SYNTAX          Unsigned32
MAX-ACCESS      not-accessible
STATUS          current
DESCRIPTION     "Table Index."
::= { leakage1Entry 1}

leakage1Name OBJECT-TYPE
SYNTAX          DisplayString
MAX-ACCESS      read-write
STATUS          current
DESCRIPTION     "Name of the leakage sensor."
::= { leakage1Entry 2}

leakage1Value OBJECT-TYPE
SYNTAX          Integer32
MAX-ACCESS      read-write
STATUS          current
DESCRIPTION     "Current value of the leakage sensor."
::= { leakage1Entry 3}

leakage1Alarm OBJECT-TYPE
SYNTAX          Unsigned32
MAX-ACCESS      read-write
STATUS          current
DESCRIPTION     "Current alarmstate of the leakage sensor."
::= { leakage1Entry 4}

leakage1Timestamp OBJECT-TYPE
SYNTAX          Integer32
MAX-ACCESS      read-write
STATUS          current
DESCRIPTION     "Timestamp of alarmstate change."
::= { leakage1Entry 10}

-------------------------------------------------------------------------------------------
-- Leakage 2.
-------------------------------------------------------------------------------------------

leakage2Table OBJECT-TYPE
SYNTAX          SEQUENCE OF Leakage2Entry
MAX-ACCESS      not-accessible
STATUS          current
DESCRIPTION     "Leakage 2 values."
::= { leakages 2 }

leakage2Entry OBJECT-TYPE
SYNTAX          Leakage2Entry
MAX-ACCESS      not-accessible
STATUS          current
DESCRIPTION     "Entry in leakage 2 table."
INDEX        { leakage2Index }
::= { leakage2Table 1 }

Leakage2Entry ::= SEQUENCE {
leakage2Index		Unsigned32,
leakage2Name		DisplayString,
leakage2Value		Unsigned32,
leakage2Alarm		Unsigned32,
leakage2Timestamp	Integer32}

leakage2Index OBJECT-TYPE
SYNTAX          Unsigned32
MAX-ACCESS      not-accessible
STATUS          current
DESCRIPTION     "Table Index."
::= { leakage2Entry 1}

leakage2Name OBJECT-TYPE
SYNTAX          DisplayString
MAX-ACCESS      read-write
STATUS          current
DESCRIPTION     "Name of the leakage sensor."
::= { leakage2Entry 2}

leakage2Value OBJECT-TYPE
SYNTAX          Integer32
MAX-ACCESS      read-write
STATUS          current
DESCRIPTION     "Current value of the leakage sensor."
::= { leakage2Entry 3}

leakage2Alarm OBJECT-TYPE
SYNTAX          Unsigned32
MAX-ACCESS      read-write
STATUS          current
DESCRIPTION     "Current alarmstate of the leakage sensor."
::= { leakage2Entry 4}

leakage2Timestamp OBJECT-TYPE
SYNTAX          Integer32
MAX-ACCESS      read-write
STATUS          current
DESCRIPTION     "Timestamp of alarmstate change."
::= { leakage2Entry 10}


-------------------------------------------------------------------------------------------
-- Leakage 3.
-------------------------------------------------------------------------------------------

leakage3Table OBJECT-TYPE
SYNTAX          SEQUENCE OF Leakage3Entry
MAX-ACCESS      not-accessible
STATUS          current
DESCRIPTION     "Leakage 3 values."
::= { leakages 3 }

leakage3Entry OBJECT-TYPE
SYNTAX          Leakage3Entry
MAX-ACCESS      not-accessible
STATUS          current
DESCRIPTION     "Entry in leakage 3 table."
INDEX        { leakage3Index }
::= { leakage3Table 1 }

Leakage3Entry ::= SEQUENCE {
leakage3Index		Unsigned32,
leakage3Name		DisplayString,
leakage3Value		Unsigned32,
leakage3Alarm		Unsigned32,
leakage3Timestamp	Integer32}

leakage3Index OBJECT-TYPE
SYNTAX          Unsigned32
MAX-ACCESS      not-accessible
STATUS          current
DESCRIPTION     "Table Index."
::= { leakage3Entry 1}

leakage3Name OBJECT-TYPE
SYNTAX          DisplayString
MAX-ACCESS      read-write
STATUS          current
DESCRIPTION     "Name of the leakage sensor."
::= { leakage3Entry 2}

leakage3Value OBJECT-TYPE
SYNTAX          Integer32
MAX-ACCESS      read-write
STATUS          current
DESCRIPTION     "Current value of the leakage sensor."
::= { leakage3Entry 3}

leakage3Alarm OBJECT-TYPE
SYNTAX          Unsigned32
MAX-ACCESS      read-write
STATUS          current
DESCRIPTION     "Current alarmstate of the leakage sensor."
::= { leakage3Entry 4}

leakage3Timestamp OBJECT-TYPE
SYNTAX          Integer32
MAX-ACCESS      read-write
STATUS          current
DESCRIPTION     "Timestamp of alarmstate change."
::= { leakage3Entry 10}

-------------------------------------------------------------------------------------------
-- Groups
-------------------------------------------------------------------------------------------

groupTable OBJECT-TYPE
SYNTAX          SEQUENCE OF GroupEntry
MAX-ACCESS      not-accessible
STATUS          current
DESCRIPTION     "Group."
::= { groups 1 }

groupEntry OBJECT-TYPE
SYNTAX          GroupEntry
MAX-ACCESS      not-accessible
STATUS          current
DESCRIPTION     "Entry in group table."
INDEX        { groupIndex }
::= { groupTable 1 }

GroupEntry ::= SEQUENCE {
groupIndex	        Unsigned32,
groupName	        DisplayString,
groupArmedState	    TruthValue}

groupIndex OBJECT-TYPE
SYNTAX          Unsigned32
MAX-ACCESS      not-accessible
STATUS          current
DESCRIPTION     "Table Index."
::= { groupEntry 1}

groupName OBJECT-TYPE
SYNTAX          DisplayString
MAX-ACCESS      read-write
STATUS          current
DESCRIPTION     "Group name."
::= { groupEntry 2}

groupArmedState OBJECT-TYPE
SYNTAX          TruthValue
MAX-ACCESS      read-write
STATUS          current
DESCRIPTION     "Group arm/disarm state."
::= { groupEntry 3}

-------------------------------------------------------------------------------------------
-- Sensor active power supplyline a
-------------------------------------------------------------------------------------------

groupActivePowerSupplyLineATable OBJECT-TYPE
SYNTAX          SEQUENCE OF GroupActivePowerSupplyLineAEntry
MAX-ACCESS      not-accessible
STATUS          current
DESCRIPTION     "Active power supplyline a values."
::= { groups 2 }

groupActivePowerSupplyLineAEntry OBJECT-TYPE
SYNTAX          GroupActivePowerSupplyLineAEntry
MAX-ACCESS      not-accessible
STATUS          current
DESCRIPTION     "Entry in active power supplyline a table."
INDEX        { groupActivePowerSupplyLineAIndex }
::= { groupActivePowerSupplyLineATable 1 }

GroupActivePowerSupplyLineAEntry ::= SEQUENCE {
groupActivePowerSupplyLineAIndex	Unsigned32,
groupActivePowerSupplyLineAValue    Integer32}

groupActivePowerSupplyLineAIndex OBJECT-TYPE
SYNTAX          Unsigned32
MAX-ACCESS      not-accessible
STATUS          current
DESCRIPTION     "Table Index."
::= { groupActivePowerSupplyLineAEntry 1}

groupActivePowerSupplyLineAValue OBJECT-TYPE
SYNTAX          Integer32
MAX-ACCESS      read-write
STATUS          current
DESCRIPTION     "Current value."
::= { groupActivePowerSupplyLineAEntry 2}

-------------------------------------------------------------------------------------------
-- Sensor active power supplyline b
-------------------------------------------------------------------------------------------

groupActivePowerSupplyLineBTable OBJECT-TYPE
SYNTAX          SEQUENCE OF GroupActivePowerSupplyLineBEntry
MAX-ACCESS      not-accessible
STATUS          current
DESCRIPTION     "Active power supplyline b values."
::= { groups 3 }

groupActivePowerSupplyLineBEntry OBJECT-TYPE
SYNTAX          GroupActivePowerSupplyLineBEntry
MAX-ACCESS      not-accessible
STATUS          current
DESCRIPTION     "Entry in active power supplyline b table."
INDEX        { groupActivePowerSupplyLineBIndex }
::= { groupActivePowerSupplyLineBTable 1 }

GroupActivePowerSupplyLineBEntry ::= SEQUENCE {
groupActivePowerSupplyLineBIndex    Unsigned32,
groupActivePowerSupplyLineBValue    Integer32}

groupActivePowerSupplyLineBIndex OBJECT-TYPE
SYNTAX          Unsigned32
MAX-ACCESS      not-accessible
STATUS          current
DESCRIPTION     "Table Index."
::= { groupActivePowerSupplyLineBEntry 1}

groupActivePowerSupplyLineBValue OBJECT-TYPE
SYNTAX          Integer32
MAX-ACCESS      read-write
STATUS          current
DESCRIPTION     "Current value."
::= { groupActivePowerSupplyLineBEntry 2}

-------------------------------------------------------------------------------------------
-- Sensor apparent power supplyline a
-------------------------------------------------------------------------------------------

groupApparentPowerSupplyLineATable OBJECT-TYPE
SYNTAX          SEQUENCE OF GroupApparentPowerSupplyLineAEntry
MAX-ACCESS      not-accessible
STATUS          current
DESCRIPTION     "Apparent power supplyline a values."
::= { groups 4 }

groupApparentPowerSupplyLineAEntry OBJECT-TYPE
SYNTAX          GroupApparentPowerSupplyLineAEntry
MAX-ACCESS      not-accessible
STATUS          current
DESCRIPTION     "Entry in apparent power supplyline a table."
INDEX        { groupApparentPowerSupplyLineAIndex }
::= { groupApparentPowerSupplyLineATable 1 }

GroupApparentPowerSupplyLineAEntry ::= SEQUENCE {
groupApparentPowerSupplyLineAIndex  Unsigned32,
groupApparentPowerSupplyLineAValue  Integer32}

groupApparentPowerSupplyLineAIndex OBJECT-TYPE
SYNTAX          Unsigned32
MAX-ACCESS      not-accessible
STATUS          current
DESCRIPTION     "Table Index."
::= { groupApparentPowerSupplyLineAEntry 1}

groupApparentPowerSupplyLineAValue OBJECT-TYPE
SYNTAX          Integer32
MAX-ACCESS      read-write
STATUS          current
DESCRIPTION     "Current value."
::= { groupApparentPowerSupplyLineAEntry 2}

-------------------------------------------------------------------------------------------
-- Sensor apparent power supplyline b
-------------------------------------------------------------------------------------------

groupApparentPowerSupplyLineBTable OBJECT-TYPE
SYNTAX          SEQUENCE OF GroupApparentPowerSupplyLineBEntry
MAX-ACCESS      not-accessible
STATUS          current
DESCRIPTION     "Apparent power supplyline b values."
::= { groups 5 }

groupApparentPowerSupplyLineBEntry OBJECT-TYPE
SYNTAX          GroupApparentPowerSupplyLineBEntry
MAX-ACCESS      not-accessible
STATUS          current
DESCRIPTION     "Entry in apparent power supplyline b table."
INDEX        { groupApparentPowerSupplyLineBIndex }
::= { groupApparentPowerSupplyLineBTable 1 }

GroupApparentPowerSupplyLineBEntry ::= SEQUENCE {
groupApparentPowerSupplyLineBIndex  Unsigned32,
groupApparentPowerSupplyLineBValue  Integer32}

groupApparentPowerSupplyLineBIndex OBJECT-TYPE
SYNTAX          Unsigned32
MAX-ACCESS      not-accessible
STATUS          current
DESCRIPTION     "Table Index."
::= { groupApparentPowerSupplyLineBEntry 1}

groupApparentPowerSupplyLineBValue OBJECT-TYPE
SYNTAX          Integer32
MAX-ACCESS      read-write
STATUS          current
DESCRIPTION     "Current value."
::= { groupApparentPowerSupplyLineBEntry 2}

-------------------------------------------------------------------------------------------
-- Sensor consumption power supplyline a
-------------------------------------------------------------------------------------------

groupConsumptionPowerSupplyLineATable OBJECT-TYPE
SYNTAX          SEQUENCE OF GroupConsumptionPowerSupplyLineAEntry
MAX-ACCESS      not-accessible
STATUS          current
DESCRIPTION     "Consumption power supplyline a values."
::= { groups 6 }

groupConsumptionPowerSupplyLineAEntry OBJECT-TYPE
SYNTAX          GroupConsumptionPowerSupplyLineAEntry
MAX-ACCESS      not-accessible
STATUS          current
DESCRIPTION     "Entry in consumption power supplyline a table."
INDEX        { groupConsumptionPowerSupplyLineAIndex }
::= { groupConsumptionPowerSupplyLineATable 1 }

GroupConsumptionPowerSupplyLineAEntry ::= SEQUENCE {
groupConsumptionPowerSupplyLineAIndex  Unsigned32,
groupConsumptionPowerSupplyLineAValue  Integer32}

groupConsumptionPowerSupplyLineAIndex OBJECT-TYPE
SYNTAX          Unsigned32
MAX-ACCESS      not-accessible
STATUS          current
DESCRIPTION     "Table Index."
::= { groupConsumptionPowerSupplyLineAEntry 1}

groupConsumptionPowerSupplyLineAValue OBJECT-TYPE
SYNTAX          Integer32
MAX-ACCESS      read-write
STATUS          current
DESCRIPTION     "Current value."
::= { groupConsumptionPowerSupplyLineAEntry 2}

-------------------------------------------------------------------------------------------
-- Sensor consumption power supplyline b
-------------------------------------------------------------------------------------------

groupConsumptionPowerSupplyLineBTable OBJECT-TYPE
SYNTAX          SEQUENCE OF GroupConsumptionPowerSupplyLineBEntry
MAX-ACCESS      not-accessible
STATUS          current
DESCRIPTION     "Consumption power supplyline b values."
::= { groups 7 }

groupConsumptionPowerSupplyLineBEntry OBJECT-TYPE
SYNTAX          GroupConsumptionPowerSupplyLineBEntry
MAX-ACCESS      not-accessible
STATUS          current
DESCRIPTION     "Entry in consumption power supplyline b table."
INDEX        { groupConsumptionPowerSupplyLineBIndex }
::= { groupConsumptionPowerSupplyLineBTable 1 }

GroupConsumptionPowerSupplyLineBEntry ::= SEQUENCE {
groupConsumptionPowerSupplyLineBIndex  Unsigned32,
groupConsumptionPowerSupplyLineBValue  Integer32}

groupConsumptionPowerSupplyLineBIndex OBJECT-TYPE
SYNTAX          Unsigned32
MAX-ACCESS      not-accessible
STATUS          current
DESCRIPTION     "Table Index."
::= { groupConsumptionPowerSupplyLineBEntry 1}

groupConsumptionPowerSupplyLineBValue OBJECT-TYPE
SYNTAX          Integer32
MAX-ACCESS      read-write
STATUS          current
DESCRIPTION     "Current value."
::= { groupConsumptionPowerSupplyLineBEntry 2}

-------------------------------------------------------------------------------------------
-- GroupStates
-------------------------------------------------------------------------------------------

groupStatesTable OBJECT-TYPE
SYNTAX          SEQUENCE OF GroupStatesEntry
MAX-ACCESS      not-accessible
STATUS          current
DESCRIPTION     "Group."
::= { groups 8 }

groupStatesEntry OBJECT-TYPE
SYNTAX          GroupStatesEntry
MAX-ACCESS      not-accessible
STATUS          current
DESCRIPTION     "Entry in group states table."
INDEX        { groupStatesIndex }
::= { groupStatesTable 1 }

GroupStatesEntry ::= SEQUENCE {
groupStatesIndex	        Unsigned32,
groupStatesArmed	        TruthValue,
groupStatesAlways	        TruthValue,
groupStatesFire	            TruthValue,
groupStatesSabotage	        TruthValue,
groupStatesSystem	        TruthValue,
groupStatesConnection	    TruthValue,
groupStatesTemperature	    TruthValue,
groupStatesHumidity	        TruthValue,
groupStatesDewPoint	        TruthValue,
groupStatesCo	            TruthValue,
groupStatesVoltage	        TruthValue,
groupStatesCurrent	        TruthValue,
groupStatesFrequency	    TruthValue,
groupStatesActivePower	    TruthValue,
groupStatesReactivePower	TruthValue,
groupStatesApparentPower    TruthValue
}

groupStatesIndex OBJECT-TYPE
SYNTAX          Unsigned32
MAX-ACCESS      not-accessible
STATUS          current
DESCRIPTION     "Table Index."
::= { groupStatesEntry 1}

groupStatesArmed OBJECT-TYPE
SYNTAX          TruthValue
MAX-ACCESS      read-write
STATUS          current
DESCRIPTION     "State for armed alarms."
::= { groupStatesEntry 2}

groupStatesAlways OBJECT-TYPE
SYNTAX          TruthValue
MAX-ACCESS      read-write
STATUS          current
DESCRIPTION     "State for always alarms."
::= { groupStatesEntry 3}

groupStatesFire OBJECT-TYPE
SYNTAX          TruthValue
MAX-ACCESS      read-write
STATUS          current
DESCRIPTION     "State for fire alarms."
::= { groupStatesEntry 4}

groupStatesSabotage OBJECT-TYPE
SYNTAX          TruthValue
MAX-ACCESS      read-write
STATUS          current
DESCRIPTION     "State for sabotage alarms."
::= { groupStatesEntry 5}

groupStatesSystem OBJECT-TYPE
SYNTAX          TruthValue
MAX-ACCESS      read-write
STATUS          current
DESCRIPTION     "State for system alarms."
::= { groupStatesEntry 6}

groupStatesConnection OBJECT-TYPE
SYNTAX          TruthValue
MAX-ACCESS      read-write
STATUS          current
DESCRIPTION     "Collective alarm for connection."
::= { groupStatesEntry 7}

groupStatesTemperature OBJECT-TYPE
SYNTAX          TruthValue
MAX-ACCESS      read-write
STATUS          current
DESCRIPTION     "Collective alarm for temperature."
::= { groupStatesEntry 8}

groupStatesHumidity OBJECT-TYPE
SYNTAX          TruthValue
MAX-ACCESS      read-write
STATUS          current
DESCRIPTION     "Collective alarm for humidity."
::= { groupStatesEntry 9}

groupStatesDewPoint OBJECT-TYPE
SYNTAX          TruthValue
MAX-ACCESS      read-write
STATUS          current
DESCRIPTION     "Collective alarm for dew point."
::= { groupStatesEntry 10}

groupStatesCo OBJECT-TYPE
SYNTAX          TruthValue
MAX-ACCESS      read-write
STATUS          current
DESCRIPTION     "Collective alarm for co."
::= { groupStatesEntry 11}

groupStatesVoltage OBJECT-TYPE
SYNTAX          TruthValue
MAX-ACCESS      read-write
STATUS          current
DESCRIPTION     "Collective alarm for voltage."
::= { groupStatesEntry 12}

groupStatesCurrent OBJECT-TYPE
SYNTAX          TruthValue
MAX-ACCESS      read-write
STATUS          current
DESCRIPTION     "Collective alarm for current."
::= { groupStatesEntry 13}

groupStatesFrequency OBJECT-TYPE
SYNTAX          TruthValue
MAX-ACCESS      read-write
STATUS          current
DESCRIPTION     "Collective alarm for frequency."
::= { groupStatesEntry 14}

groupStatesActivePower OBJECT-TYPE
SYNTAX          TruthValue
MAX-ACCESS      read-write
STATUS          current
DESCRIPTION     "Collective alarm for active power."
::= { groupStatesEntry 15}

groupStatesReactivePower OBJECT-TYPE
SYNTAX          TruthValue
MAX-ACCESS      read-write
STATUS          current
DESCRIPTION     "Collective alarm for reactive power."
::= { groupStatesEntry 16}

groupStatesApparentPower OBJECT-TYPE
SYNTAX          TruthValue
MAX-ACCESS      read-write
STATUS          current
DESCRIPTION     "Collective alarm for apparent power."
::= { groupStatesEntry 17}

----------------------------------------------------------------
-- Logbooks
-------------------------------------------------------------------------------------------

-------------------------------------------------------------------------------------------
-- System-Logbook
-------------------------------------------------------------------------------------------

systemLogbookTable OBJECT-TYPE
SYNTAX          SEQUENCE OF SystemLogbookEntry
MAX-ACCESS      not-accessible
STATUS          current
DESCRIPTION     "SystemLogbook Entrys."
::= { logbook 1 }

systemLogbookEntry OBJECT-TYPE
SYNTAX          SystemLogbookEntry
MAX-ACCESS      not-accessible
STATUS          current
DESCRIPTION     "Entry in SystemLogboo table."
INDEX        { systemLogbookIndex }
::= { systemLogbookTable 1 }

SystemLogbookEntry ::= SEQUENCE {
systemLogbookIndex      Unsigned32,
systemLogbookDate       DisplayString,
systemLogbookFunction   DisplayString,
systemLogbookDetail     DisplayString,
systemLogbookType       Unsigned32}

systemLogbookIndex OBJECT-TYPE
SYNTAX          Unsigned32
MAX-ACCESS      not-accessible
STATUS          current
DESCRIPTION     "Table Index."
::= { systemLogbookEntry 1}

systemLogbookDate OBJECT-TYPE
SYNTAX          DisplayString
MAX-ACCESS      read-write
STATUS          current
DESCRIPTION     "Date as UNIX timestamp."
::= { systemLogbookEntry 2}

systemLogbookFunction OBJECT-TYPE
SYNTAX          DisplayString
MAX-ACCESS      read-write
STATUS          current
DESCRIPTION     "Category of the logbook entry."
::= { systemLogbookEntry 3}

systemLogbookDetail OBJECT-TYPE
SYNTAX          DisplayString
MAX-ACCESS      read-write
STATUS          current
DESCRIPTION     "Detail field."
::= { systemLogbookEntry 4}

systemLogbookType OBJECT-TYPE
SYNTAX          Unsigned32
MAX-ACCESS      read-write
STATUS          current
DESCRIPTION     "Type Of the logbook entry."
::= { systemLogbookEntry 5}

-------------------------------------------------------------------------------------------
-- Access-Logbook
-------------------------------------------------------------------------------------------

accessLogbookTable OBJECT-TYPE
SYNTAX          SEQUENCE OF AccessLogbookEntry
MAX-ACCESS      not-accessible
STATUS          current
DESCRIPTION     "AccessLogbook Entrys."
::= { logbook 2 }

accessLogbookEntry OBJECT-TYPE
SYNTAX          AccessLogbookEntry
MAX-ACCESS      not-accessible
STATUS          current
DESCRIPTION     "Entry in AccessLogbook table."
INDEX        { accessLogbookIndex }
::= { accessLogbookTable 1 }

AccessLogbookEntry ::= SEQUENCE {
accessLogbookIndex      Unsigned32,
accessLogbookDate       DisplayString,
accessLogbookDoor       DisplayString,
accessLogbookUser       DisplayString,
accessLogbookState      Unsigned32,
accessLogbookDetail     DisplayString}

accessLogbookIndex OBJECT-TYPE
SYNTAX          Unsigned32
MAX-ACCESS      not-accessible
STATUS          current
DESCRIPTION     "Table Index."
::= { accessLogbookEntry 1}

accessLogbookDate OBJECT-TYPE
SYNTAX          DisplayString
MAX-ACCESS      read-write
STATUS          current
DESCRIPTION     "Date as UNIX timestamp."
::= { accessLogbookEntry 2}

accessLogbookDoor OBJECT-TYPE
SYNTAX          DisplayString
MAX-ACCESS      read-write
STATUS          current
DESCRIPTION     "Name of the door."
::= { accessLogbookEntry 3}

accessLogbookUser OBJECT-TYPE
SYNTAX          DisplayString
MAX-ACCESS      read-write
STATUS          current
DESCRIPTION     "Name of the user."
::= { accessLogbookEntry 4}

accessLogbookState OBJECT-TYPE
SYNTAX          Unsigned32
MAX-ACCESS      read-write
STATUS          current
DESCRIPTION     "State (0 = closed, 1 = open) ."
::= { accessLogbookEntry 5}

accessLogbookDetail OBJECT-TYPE
SYNTAX          DisplayString
MAX-ACCESS      read-write
STATUS          current
DESCRIPTION     "Detail field."
::= { accessLogbookEntry 6}

-------------------------------------------------------------------------------------------
-- Event-Logbook
-------------------------------------------------------------------------------------------

eventLogbookTable OBJECT-TYPE
SYNTAX          SEQUENCE OF EventLogbookEntry
MAX-ACCESS      not-accessible
STATUS          current
DESCRIPTION     "EventLogbook Entrys."
::= { logbook 3 }

eventLogbookEntry OBJECT-TYPE
SYNTAX          EventLogbookEntry
MAX-ACCESS      not-accessible
STATUS          current
DESCRIPTION     "Entry in EventLogbook table."
INDEX        { eventLogbookIndex }
::= { eventLogbookTable 1 }

EventLogbookEntry ::= SEQUENCE {
eventLogbookIndex      Unsigned32,
eventLogbookDate       DisplayString,
eventLogbookFunction   DisplayString,
eventLogbookUser       DisplayString,
eventLogbookDetail     DisplayString}

eventLogbookIndex OBJECT-TYPE
SYNTAX          Unsigned32
MAX-ACCESS      not-accessible
STATUS          current
DESCRIPTION     "Table Index."
::= { eventLogbookEntry 1}

eventLogbookDate OBJECT-TYPE
SYNTAX          DisplayString
MAX-ACCESS      read-write
STATUS          current
DESCRIPTION     "Date as UNIX timestamp."
::= { eventLogbookEntry 2}

eventLogbookFunction OBJECT-TYPE
SYNTAX          DisplayString
MAX-ACCESS      read-write
STATUS          current
DESCRIPTION     "Category of the logbook entry."
::= { eventLogbookEntry 3}

eventLogbookUser OBJECT-TYPE
SYNTAX          DisplayString
MAX-ACCESS      read-write
STATUS          current
DESCRIPTION     "Username field."
::= { eventLogbookEntry 4}

eventLogbookDetail OBJECT-TYPE
SYNTAX          DisplayString
MAX-ACCESS      read-write
STATUS          current
DESCRIPTION     "Detail field."
::= { eventLogbookEntry 5}

-------------------------------------------------------------------------------------------
-- Rack units
-------------------------------------------------------------------------------------------

rackUnitTable OBJECT-TYPE
SYNTAX          SEQUENCE OF RackUnitEntry
MAX-ACCESS      not-accessible
STATUS          current
DESCRIPTION     "Rach units."
::= { rackunits 1 }

rackUnitEntry OBJECT-TYPE
SYNTAX          RackUnitEntry
MAX-ACCESS      not-accessible
STATUS          current
DESCRIPTION     "Entry in rackUnit table."
INDEX        { rackUnitIndex }
::= { rackUnitTable 1 }

RackUnitEntry ::= SEQUENCE {
rackUnitIndex   Unsigned32,
rackUnitName    DisplayString}

rackUnitIndex OBJECT-TYPE
SYNTAX          Unsigned32
MAX-ACCESS      not-accessible
STATUS          current
DESCRIPTION     "Table Index."
::= { rackUnitEntry 1}

rackUnitName OBJECT-TYPE
SYNTAX          DisplayString
MAX-ACCESS      read-write
STATUS          current
DESCRIPTION     "Rack unit name."
::= { rackUnitEntry 2}

-------------------------------------------------------------------------------------------
-- Sensor active power supplyline a
-------------------------------------------------------------------------------------------

rackUnitActivePowerSupplyLineATable OBJECT-TYPE
SYNTAX          SEQUENCE OF RackUnitActivePowerSupplyLineAEntry
MAX-ACCESS      not-accessible
STATUS          current
DESCRIPTION     "Active power supplyline a values."
::= { rackunits 2 }

rackUnitActivePowerSupplyLineAEntry OBJECT-TYPE
SYNTAX          RackUnitActivePowerSupplyLineAEntry
MAX-ACCESS      not-accessible
STATUS          current
DESCRIPTION     "Entry in active power supplyline a table."
INDEX        { rackUnitActivePowerSupplyLineAIndex }
::= { rackUnitActivePowerSupplyLineATable 1 }

RackUnitActivePowerSupplyLineAEntry ::= SEQUENCE {
rackUnitActivePowerSupplyLineAIndex	Unsigned32,
rackUnitActivePowerSupplyLineAValue    Integer32,
rackUnitActivePowerSupplyLineAAlarm    Unsigned32,
rackUnitActivePowerSupplyLineAMax      Integer32}

rackUnitActivePowerSupplyLineAIndex OBJECT-TYPE
SYNTAX          Unsigned32
MAX-ACCESS      not-accessible
STATUS          current
DESCRIPTION     "Table Index."
::= { rackUnitActivePowerSupplyLineAEntry 1}

rackUnitActivePowerSupplyLineAValue OBJECT-TYPE
SYNTAX          Integer32
MAX-ACCESS      read-write
STATUS          current
DESCRIPTION     "Current value."
::= { rackUnitActivePowerSupplyLineAEntry 2}

rackUnitActivePowerSupplyLineAAlarm OBJECT-TYPE
SYNTAX          Unsigned32
MAX-ACCESS      read-write
STATUS          current
DESCRIPTION     "Current alarmstate."
::= { rackUnitActivePowerSupplyLineAEntry 3}

rackUnitActivePowerSupplyLineAMax OBJECT-TYPE
SYNTAX          Integer32
MAX-ACCESS      read-write
STATUS          current
DESCRIPTION     "Max. threshold of this value."
::= { rackUnitActivePowerSupplyLineAEntry 5}

-------------------------------------------------------------------------------------------
-- Sensor active power supplyline b
-------------------------------------------------------------------------------------------

rackUnitActivePowerSupplyLineBTable OBJECT-TYPE
SYNTAX          SEQUENCE OF RackUnitActivePowerSupplyLineBEntry
MAX-ACCESS      not-accessible
STATUS          current
DESCRIPTION     "Active power supplyline b values."
::= { rackunits 3 }

rackUnitActivePowerSupplyLineBEntry OBJECT-TYPE
SYNTAX          RackUnitActivePowerSupplyLineBEntry
MAX-ACCESS      not-accessible
STATUS          current
DESCRIPTION     "Entry in active power supplyline b table."
INDEX        { rackUnitActivePowerSupplyLineBIndex }
::= { rackUnitActivePowerSupplyLineBTable 1 }

RackUnitActivePowerSupplyLineBEntry ::= SEQUENCE {
rackUnitActivePowerSupplyLineBIndex    Unsigned32,
rackUnitActivePowerSupplyLineBValue    Integer32,
rackUnitActivePowerSupplyLineBAlarm    Unsigned32,
rackUnitActivePowerSupplyLineBMax      Integer32}

rackUnitActivePowerSupplyLineBIndex OBJECT-TYPE
SYNTAX          Unsigned32
MAX-ACCESS      not-accessible
STATUS          current
DESCRIPTION     "Table Index."
::= { rackUnitActivePowerSupplyLineBEntry 1}

rackUnitActivePowerSupplyLineBValue OBJECT-TYPE
SYNTAX          Integer32
MAX-ACCESS      read-write
STATUS          current
DESCRIPTION     "Current value."
::= { rackUnitActivePowerSupplyLineBEntry 2}

rackUnitActivePowerSupplyLineBAlarm OBJECT-TYPE
SYNTAX          Unsigned32
MAX-ACCESS      read-write
STATUS          current
DESCRIPTION     "Current alarmstate."
::= { rackUnitActivePowerSupplyLineBEntry 3}

rackUnitActivePowerSupplyLineBMax OBJECT-TYPE
SYNTAX          Integer32
MAX-ACCESS      read-write
STATUS          current
DESCRIPTION     "Max. threshold of this value."
::= { rackUnitActivePowerSupplyLineBEntry 5}

-------------------------------------------------------------------------------------------
-- Sensor apparent power supplyline a
-------------------------------------------------------------------------------------------

rackUnitApparentPowerSupplyLineATable OBJECT-TYPE
SYNTAX          SEQUENCE OF RackUnitApparentPowerSupplyLineAEntry
MAX-ACCESS      not-accessible
STATUS          current
DESCRIPTION     "Apparent power supplyline a values."
::= { rackunits 4 }

rackUnitApparentPowerSupplyLineAEntry OBJECT-TYPE
SYNTAX          RackUnitApparentPowerSupplyLineAEntry
MAX-ACCESS      not-accessible
STATUS          current
DESCRIPTION     "Entry in apparent power supplyline a table."
INDEX        { rackUnitApparentPowerSupplyLineAIndex }
::= { rackUnitApparentPowerSupplyLineATable 1 }

RackUnitApparentPowerSupplyLineAEntry ::= SEQUENCE {
rackUnitApparentPowerSupplyLineAIndex  Unsigned32,
rackUnitApparentPowerSupplyLineAValue  Integer32}

rackUnitApparentPowerSupplyLineAIndex OBJECT-TYPE
SYNTAX          Unsigned32
MAX-ACCESS      not-accessible
STATUS          current
DESCRIPTION     "Table Index."
::= { rackUnitApparentPowerSupplyLineAEntry 1}

rackUnitApparentPowerSupplyLineAValue OBJECT-TYPE
SYNTAX          Integer32
MAX-ACCESS      read-write
STATUS          current
DESCRIPTION     "Current value."
::= { rackUnitApparentPowerSupplyLineAEntry 2}

-------------------------------------------------------------------------------------------
-- Sensor apparent power supplyline b
-------------------------------------------------------------------------------------------

rackUnitApparentPowerSupplyLineBTable OBJECT-TYPE
SYNTAX          SEQUENCE OF RackUnitApparentPowerSupplyLineBEntry
MAX-ACCESS      not-accessible
STATUS          current
DESCRIPTION     "Apparent power supplyline b values."
::= { rackunits 5 }

rackUnitApparentPowerSupplyLineBEntry OBJECT-TYPE
SYNTAX          RackUnitApparentPowerSupplyLineBEntry
MAX-ACCESS      not-accessible
STATUS          current
DESCRIPTION     "Entry in apparent power supplyline b table."
INDEX        { rackUnitApparentPowerSupplyLineBIndex }
::= { rackUnitApparentPowerSupplyLineBTable 1 }

RackUnitApparentPowerSupplyLineBEntry ::= SEQUENCE {
rackUnitApparentPowerSupplyLineBIndex  Unsigned32,
rackUnitApparentPowerSupplyLineBValue  Integer32}

rackUnitApparentPowerSupplyLineBIndex OBJECT-TYPE
SYNTAX          Unsigned32
MAX-ACCESS      not-accessible
STATUS          current
DESCRIPTION     "Table Index."
::= { rackUnitApparentPowerSupplyLineBEntry 1}

rackUnitApparentPowerSupplyLineBValue OBJECT-TYPE
SYNTAX          Integer32
MAX-ACCESS      read-write
STATUS          current
DESCRIPTION     "Current value."
::= { rackUnitApparentPowerSupplyLineBEntry 2}

-------------------------------------------------------------------------------------------
-- Sensor consumption power supplyline a
-------------------------------------------------------------------------------------------

rackUnitConsumptionPowerSupplyLineATable OBJECT-TYPE
SYNTAX          SEQUENCE OF RackUnitConsumptionPowerSupplyLineAEntry
MAX-ACCESS      not-accessible
STATUS          current
DESCRIPTION     "Consumption power supplyline a values."
::= { rackunits 6 }

rackUnitConsumptionPowerSupplyLineAEntry OBJECT-TYPE
SYNTAX          RackUnitConsumptionPowerSupplyLineAEntry
MAX-ACCESS      not-accessible
STATUS          current
DESCRIPTION     "Entry in consumption power supplyline a table."
INDEX        { rackUnitConsumptionPowerSupplyLineAIndex }
::= { rackUnitConsumptionPowerSupplyLineATable 1 }

RackUnitConsumptionPowerSupplyLineAEntry ::= SEQUENCE {
rackUnitConsumptionPowerSupplyLineAIndex  Unsigned32,
rackUnitConsumptionPowerSupplyLineAValue  Integer32}

rackUnitConsumptionPowerSupplyLineAIndex OBJECT-TYPE
SYNTAX          Unsigned32
MAX-ACCESS      not-accessible
STATUS          current
DESCRIPTION     "Table Index."
::= { rackUnitConsumptionPowerSupplyLineAEntry 1}

rackUnitConsumptionPowerSupplyLineAValue OBJECT-TYPE
SYNTAX          Integer32
MAX-ACCESS      read-write
STATUS          current
DESCRIPTION     "Current value."
::= { rackUnitConsumptionPowerSupplyLineAEntry 2}

-------------------------------------------------------------------------------------------
-- Sensor consumption power supplyline b
-------------------------------------------------------------------------------------------

rackUnitConsumptionPowerSupplyLineBTable OBJECT-TYPE
SYNTAX          SEQUENCE OF RackUnitConsumptionPowerSupplyLineBEntry
MAX-ACCESS      not-accessible
STATUS          current
DESCRIPTION     "Consumption power supplyline b values."
::= { rackunits 7 }

rackUnitConsumptionPowerSupplyLineBEntry OBJECT-TYPE
SYNTAX          RackUnitConsumptionPowerSupplyLineBEntry
MAX-ACCESS      not-accessible
STATUS          current
DESCRIPTION     "Entry in consumption power supplyline b table."
INDEX        { rackUnitConsumptionPowerSupplyLineBIndex }
::= { rackUnitConsumptionPowerSupplyLineBTable 1 }

RackUnitConsumptionPowerSupplyLineBEntry ::= SEQUENCE {
rackUnitConsumptionPowerSupplyLineBIndex  Unsigned32,
rackUnitConsumptionPowerSupplyLineBValue  Integer32}

rackUnitConsumptionPowerSupplyLineBIndex OBJECT-TYPE
SYNTAX          Unsigned32
MAX-ACCESS      not-accessible
STATUS          current
DESCRIPTION     "Table Index."
::= { rackUnitConsumptionPowerSupplyLineBEntry 1}

rackUnitConsumptionPowerSupplyLineBValue OBJECT-TYPE
SYNTAX          Integer32
MAX-ACCESS      read-write
STATUS          current
DESCRIPTION     "Current value."
::= { rackUnitConsumptionPowerSupplyLineBEntry 2}

-------------------------------------------------------------------------------------------
-- Trap Objects (for NOTIFICATION-TYPE)
-------------------------------------------------------------------------------------------

-- AlarmStateChangeEventDevice Trap Objects
alarmStateChangeDeviceIndex OBJECT-TYPE
SYNTAX Unsigned32
MAX-ACCESS accessible-for-notify
STATUS current
DESCRIPTION "Device index for alarm state change trap."
::= { trapObjects 1}

alarmStateChangeDeviceTimestamp OBJECT-TYPE
SYNTAX Unsigned32
MAX-ACCESS accessible-for-notify
STATUS current
DESCRIPTION "Timestamp for alarm state change trap (UNIX timestamp)."
::= { trapObjects 2}

alarmStateChangeDeviceAlarmState OBJECT-TYPE
SYNTAX Unsigned32
MAX-ACCESS accessible-for-notify
STATUS current
DESCRIPTION "Alarm state for trap."
::= { trapObjects 3}

alarmStateChangeDeviceAlarmName OBJECT-TYPE
SYNTAX Unsigned32
MAX-ACCESS accessible-for-notify
STATUS current
DESCRIPTION "Alarm name for trap."
::= { trapObjects 4}

alarmStateChangeDeviceAlarmDescription OBJECT-TYPE
SYNTAX Unsigned32
MAX-ACCESS accessible-for-notify
STATUS current
DESCRIPTION "Alarm description for trap."
::= { trapObjects 5}

alarmStateChangeDeviceAddress OBJECT-TYPE
SYNTAX Unsigned32
MAX-ACCESS accessible-for-notify
STATUS current
DESCRIPTION "Device address for trap."
::= { trapObjects 6}

alarmStateChangeDeviceAlarmtype OBJECT-TYPE
SYNTAX Unsigned32
MAX-ACCESS accessible-for-notify
STATUS current
DESCRIPTION "Device alarm type for trap."
::= { trapObjects 7}

alarmStateChangeDeviceAlarmMeasurement OBJECT-TYPE
SYNTAX Unsigned32
MAX-ACCESS accessible-for-notify
STATUS current
DESCRIPTION "Alarm measurement for trap."
::= { trapObjects 8}

-- StructuredAlarmEvent Trap Objects
structuredAlarmEventTimestamp OBJECT-TYPE
SYNTAX Unsigned32
MAX-ACCESS accessible-for-notify
STATUS current
DESCRIPTION "Timestamp for structured alarm event (UNIX timestamp)."
::= { trapObjects 10}

structuredAlarmEventAlarmState OBJECT-TYPE
SYNTAX Unsigned32
MAX-ACCESS accessible-for-notify
STATUS current
DESCRIPTION "Alarm state for structured alarm event."
::= { trapObjects 11}

structuredAlarmEventSensorName OBJECT-TYPE
SYNTAX Unsigned32
MAX-ACCESS accessible-for-notify
STATUS current
DESCRIPTION "Sensor name for structured alarm event."
::= { trapObjects 12}

structuredAlarmEventGroupName OBJECT-TYPE
SYNTAX Unsigned32
MAX-ACCESS accessible-for-notify
STATUS current
DESCRIPTION "Group name for structured alarm event."
::= { trapObjects 13}

structuredAlarmEventDeviceName OBJECT-TYPE
SYNTAX Unsigned32
MAX-ACCESS accessible-for-notify
STATUS current
DESCRIPTION "Device name for structured alarm event."
::= { trapObjects 14}

structuredAlarmEventMeasurement OBJECT-TYPE
SYNTAX Unsigned32
MAX-ACCESS accessible-for-notify
STATUS current
DESCRIPTION "Measurement for structured alarm event."
::= { trapObjects 15}

structuredAlarmEventUnit OBJECT-TYPE
SYNTAX Unsigned32
MAX-ACCESS accessible-for-notify
STATUS current
DESCRIPTION "Measurement unit for structured alarm event."
::= { trapObjects 16}

-- StructuredAccessEvent Trap Objects
structuredAccessEventTimestamp OBJECT-TYPE
SYNTAX Unsigned32
MAX-ACCESS accessible-for-notify
STATUS current
DESCRIPTION "Timestamp for structured access event (UNIX timestamp)."
::= { trapObjects 20}

structuredAccessEventState OBJECT-TYPE
SYNTAX Unsigned32
MAX-ACCESS accessible-for-notify
STATUS current
DESCRIPTION "Booking state for structured access event."
::= { trapObjects 21}

structuredAccessEventDoorlockName OBJECT-TYPE
SYNTAX Unsigned32
MAX-ACCESS accessible-for-notify
STATUS current
DESCRIPTION "Doorlock name for structured access event."
::= { trapObjects 22}

structuredAccessEventUserName OBJECT-TYPE
SYNTAX Unsigned32
MAX-ACCESS accessible-for-notify
STATUS current
DESCRIPTION "User name for structured access event."
::= { trapObjects 23}

structuredAccessEventDetail OBJECT-TYPE
SYNTAX Unsigned32
MAX-ACCESS accessible-for-notify
STATUS current
DESCRIPTION "Detail of structured access event."
::= { trapObjects 24}

-- AlarmStateChangeEventGroup Trap Objects
alarmStateChangeGroupIndex OBJECT-TYPE
SYNTAX Unsigned32
MAX-ACCESS accessible-for-notify
STATUS current
DESCRIPTION "Group index for alarm state change trap."
::= { trapObjects 30}

alarmStateChangeGroupTimestamp OBJECT-TYPE
SYNTAX Unsigned32
MAX-ACCESS accessible-for-notify
STATUS current
DESCRIPTION "Timestamp for group alarm state change (UNIX timestamp)."
::= { trapObjects 31}

alarmStateChangeGroupAlarmState OBJECT-TYPE
SYNTAX Unsigned32
MAX-ACCESS accessible-for-notify
STATUS current
DESCRIPTION "Alarm state for group trap."
::= { trapObjects 32}

alarmStateChangeGroupAlarmName OBJECT-TYPE
SYNTAX Unsigned32
MAX-ACCESS accessible-for-notify
STATUS current
DESCRIPTION "Alarm name for group trap."
::= { trapObjects 33}

alarmStateChangeGroupAlarmDescription OBJECT-TYPE
SYNTAX Unsigned32
MAX-ACCESS accessible-for-notify
STATUS current
DESCRIPTION "Alarm description for group trap."
::= { trapObjects 34}

alarmStateChangeGroupAlarmtype OBJECT-TYPE
SYNTAX Unsigned32
MAX-ACCESS accessible-for-notify
STATUS current
DESCRIPTION "Group alarm type for trap."
::= { trapObjects 35}

alarmStateChangeGroupAlarmMeasurement OBJECT-TYPE
SYNTAX Unsigned32
MAX-ACCESS accessible-for-notify
STATUS current
DESCRIPTION "Alarm measurement for group trap."
::= { trapObjects 36}

-------------------------------------------------------------------------------------------
-- Login-Event
-------------------------------------------------------------------------------------------

loginEvent NOTIFICATION-TYPE
	STATUS current
	DESCRIPTION "SNMP Trap for each Login-Events"
	::= { kentixdevices 100 }
	
-------------------------------------------------------------------------------------------
-- AlarmStateChangeDevice-Event
-------------------------------------------------------------------------------------------

alarmStateChangeEventDevice NOTIFICATION-TYPE
	OBJECTS{
	alarmStateChangeDeviceIndex,
	alarmStateChangeDeviceTimestamp,
	alarmStateChangeDeviceAlarmState,
	alarmStateChangeDeviceAlarmName,
	alarmStateChangeDeviceAlarmDescription,
	alarmStateChangeDeviceAddress,
	alarmStateChangeDeviceAlarmtype,
	alarmStateChangeDeviceAlarmMeasurement
	}
	STATUS current
	DESCRIPTION "SNMP Trap for each change in an alarmstate"
	::= { kentixdevices 101 }

-------------------------------------------------------------------------------------------
-- Heartbeat-Event
-------------------------------------------------------------------------------------------

heartbeat NOTIFICATION-TYPE
	STATUS current
	DESCRIPTION "Heartbeat Trap"
	::= { kentixdevices 102 }

-------------------------------------------------------------------------------------------
-- Structured Alarm-Event
-------------------------------------------------------------------------------------------

structredAlarmEvent NOTIFICATION-TYPE
	OBJECTS{
	structuredAlarmEventTimestamp,
	structuredAlarmEventAlarmState,
	structuredAlarmEventSensorName,
	structuredAlarmEventGroupName,
	structuredAlarmEventDeviceName,
	structuredAlarmEventMeasurement,
	structuredAlarmEventUnit
	}
	STATUS current
	DESCRIPTION "Structured alarm trap"
	::= { kentixdevices 103 }

-------------------------------------------------------------------------------------------
-- Alarm-Event
-------------------------------------------------------------------------------------------

alarmEvent NOTIFICATION-TYPE
	STATUS current
	DESCRIPTION "Alarm Trap"
	::= { kentixdevices 104 }

-------------------------------------------------------------------------------------------
-- Structured Access-Event
-------------------------------------------------------------------------------------------

structredAccessEvent NOTIFICATION-TYPE
	OBJECTS{
	structuredAccessEventTimestamp,
	structuredAccessEventState,
	structuredAccessEventDoorlockName,
	structuredAccessEventUserName,
	structuredAccessEventDetail
	}
	STATUS current
	DESCRIPTION "Structured alarm trap"
	::= { kentixdevices 105 }

-------------------------------------------------------------------------------------------
-- Alarm-Event
-------------------------------------------------------------------------------------------

accessEvent NOTIFICATION-TYPE
	STATUS current
	DESCRIPTION "Alarm Trap"
	::= { kentixdevices 106 }

-------------------------------------------------------------------------------------------
-- AlarmStateChangeGroup-Event
-------------------------------------------------------------------------------------------

alarmStateChangeEventGroup NOTIFICATION-TYPE
	OBJECTS{
	alarmStateChangeGroupIndex,
	alarmStateChangeGroupTimestamp,
	alarmStateChangeGroupAlarmState,
	alarmStateChangeGroupAlarmName,
	alarmStateChangeGroupAlarmDescription,
	alarmStateChangeGroupAlarmtype,
	alarmStateChangeGroupAlarmMeasurement
	}
	STATUS current
	DESCRIPTION "SNMP Trap for each change in an alarmstate"
	::= { kentixdevices 107 }

END
