-- *****************************************************************
-- CISCO-FC-FE-CAPABILITY.my:  Cisco Fibre Channel Fibre Element MIB
-- AGENT-CAPABILITIES
--   
-- May 2005, Srini Kode
--   
-- Copyright (c) 2005, 2015 by cisco Systems Inc.
-- All rights reserved.
--   
-- *****************************************************************

CISCO-FC-FE-CAPABILITY DEFINITIONS ::= BEGIN

IMPORTS
    MODULE-IDENTITY
        FROM SNMPv2-SMI
    AGENT-CAPABILITIES
        FROM SNMPv2-CONF
    CiscoMilliSeconds
        FROM CISCO-TC
    ciscoAgentCapability
        FROM CISCO-SMI;


ciscoFcFeCapability MODULE-IDENTITY
    LAST-UPDATED    "201506230000Z"
    ORGANIZATION    "Cisco Systems, Inc."
    CONTACT-INFO
            "Cisco Systems
            Customer Service

            Postal: 170 W Tasman Drive
            San Jose, CA  95134
            USA

            Tel: +1 800 553-NETS

            E-mail: cs-san@cisco.com"
    DESCRIPTION
        "Agent capabilities for the CISCO-FC-FE-MIB."
    REVISION        "201506230000Z"
    DESCRIPTION
        "Added capability statement ciscoFcFeCapabilityV06R0213PMds."
    REVISION        "200505240000Z"
    DESCRIPTION
        "Agent capabilities for Cisco MDS 3.0."
    ::= { ciscoAgentCapability 627 }



ciscoFcFeCapabilityMDS3R0 AGENT-CAPABILITIES
    PRODUCT-RELEASE "Cisco MDS 3.0(1)"
    STATUS          current
    DESCRIPTION
        "Cisco FC FE MIB capabilities."

    SUPPORTS        CISCO-FC-FE-MIB
    INCLUDES        {
                        fcFeGroup,
                        fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2,
                        fcIfStatGroup,
                        fcIfErrorGroupRev1,
                        fcIfGroupRev3,
                        fcIfRNIDInfoGroup,
                        fcotInfoNotificationGroup,
                        fcIfGigEInfoGroup
                    }
    ::= { ciscoFcFeCapability 1 }

ciscoFcFeCapabilityV06R0213PMds AGENT-CAPABILITIES
    PRODUCT-RELEASE "Cisco NX-OS 6.2(13) on MDS series devices."
    STATUS          current
    DESCRIPTION
        "CISCO-FC-FE-MIB capabilities."

    SUPPORTS        CISCO-FC-FE-MIB
    INCLUDES        { 
    					fcFeGroupRev1,
                      	fcIfGroup,
                        fcTrunkIfGroup,
                        fcIfLoginGroup,
                        fcIfElpGroup,
                        fcIfErrorGroup,
                        fcIfC2AccountingGroup,
                        fcIfC3AccountingGroup,
                        fcIfCfAccountingGroup,
                        fcIfNotificationGroup,
                        fcIfGroupRev1,
                        fcIfCapGroupRev1,
                        fcIfGroupRev2,
                        fcIfStatGroup,
                        fcIfErrorGroupRev1,
                        fcIfGroupRev3,
                        fcIfRNIDInfoGroup,
                        fcotInfoNotificationGroup,
                        fcIfGigEInfoGroup,
                        fcIfInfoGroup,
                        fcIfGigEinfoExtGroup,
                        fcIfBbScnGroup,
                        fcIfCapableGroup,
                        fcIfInfoPortGroup,
                        fcIfFlapCtrlConfigGroup,
                        fcIfModuleGroupRev1,
                        fcIfGigEinfoExtGroupRev1,
                        fcIfErrorGroupRev2,
                        fcIfErrorGroupRev3,
                        fcIfGroupRev4,
                        fcIfErrorGroupRev4,
                        fcFeGroupRev1,
                        fcIfErrorGroupRev5,
                        fcIfGigEinfoExtGroupRev2,
                        fcIfGigEinfoExtGroupRev3
    			    }
    VARIATION       fcIffPortCongestionDropTimeout
    SYNTAX          CiscoMilliSeconds (100..500)
    DEFVAL          { 500 }
    DESCRIPTION
        "Only a limited set of value is supported for
        all the platforms like m9506, m9509, m9513, m9710,
        m9706, m9250, m9148S, m9148, m9396S, m9222i, m9134,
        m9124. The value must be multiple of 10 between
        100 to 500.
        A value of 500 indicates that congestion drop is 
        the default value in the enabled mode."

    VARIATION       fcIfePortCongestionDropTimeout
    SYNTAX          CiscoMilliSeconds (100..500)
    DEFVAL          { 500 }
    DESCRIPTION
        "Only a limited set of value is supported for
        all the platforms like m9506, m9509, m9513, m9710,
        m9706, m9250, m9148S, m9148, m9396S, m9222i, m9134,
        m9124. The value must be multiple of 10 between
        100 to 500.
        A value of 500 indicates that congestion drop is 
        the default value in the enabled mode."

    VARIATION       fcIffPortNoCreditDropTimeout
    SYNTAX          CiscoMilliSeconds (0 | 1..500)
    DEFVAL          { 0 }    
    DESCRIPTION
        "Only a limited set of value is supported. 
        Implementation supports values from 1 to 500 for
        the platforms like m9710, m9706, m9250, m9148S. 
        Implementation supports values from 100 to 500 for
        the platforms like m9506, m9509, m9513, m9148, m9222i,
        m9134, m9124. The value must be multiple of 100
        between 1 to 500.
        A value of zero indicates that no-credit-drop
        is disabled.
        A value of 500 indicates that no-credit-drop is the default 
        value in the enabled mode."

    VARIATION       fcIfePortSlowportMonitorTimeout
    SYNTAX          CiscoMilliSeconds (0 | 1..500)
    DEFVAL          { 0 }
    DESCRIPTION
        "Only a limited set of value is supported.
        Implementation supports values from 1 to 500 for
        the platforms like m9710, m9706, m9250, m9148S.
        Implementation supports values from 1 to 100 for
        the platforms like m9506, m9509, m9513. 
        Implementation does not support platforms like
        m9148, m9222i, m9134, m9124.
        A value of zero indicates that slowport-monitor
        is disabled.
        A value of 50 indicates that slowport-monitor 
        is the default value in the enabled mode."

    VARIATION       fcIffPortSlowportMonitorTimeout
    SYNTAX          CiscoMilliSeconds (0 | 1..500)
    DEFVAL          { 0 }
    DESCRIPTION
        "Only a limited set of value is supported.
        Implementation supports values from 1 to 500 for
        the platforms like m9710, m9706, m9250, m9148S.
        Implementation supports values from 1 to 100 for
        the platforms like m9506, m9509, m9513. 
        Implementation does not support platforms like
        m9148, m9222i, m9134, m9124.
        A value of zero indicates that slowport-monitor
        is disabled.
        A value of 50 indicates that slowport-monitor 
        is the default value in the enabled mode."

    ::= { ciscoFcFeCapability 2 }

END
